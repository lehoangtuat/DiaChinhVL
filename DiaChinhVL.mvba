Attribute VB_Name = "TachThua22"
Option Explicit

' ====================================================================
'  MACRO VE SO DO TACH THUA - MAU SO 22  (MicroStation V8i SS3)
'
'  B1_ChonThua : Mo file BAN DO, chon >= 2 thua SAU TACH (shape) roi chay.
'                Macro tu gop thanh thua goc, danh so dinh, tinh canh,
'                dien tich va luu tam vao %TEMP%\tachthua_mau22.txt
'  B2_VeSoDo   : Mo file MAU 22, chay macro, bam (snap) 2 goc khung
'                muc 3 (goc DUOI-TRAI roi goc TREN-PHAI cua khung chua
'                3.1 + 3.2 + 3.3). Macro ve so do 3.1, 3.2 va dien bang 3.3.
'
'  Quy tac danh so: bat dau tu dinh o phia BAC nhat, theo chieu KIM DONG HO.
'  Dinh moi tren duong chia danh so tiep theo (7', 8'...).
' ====================================================================

Private Const tol As Double = 0.01        ' dung sai trung diem (m)
Private Const COL_TOL As Double = 0.02    ' dung sai thang hang (m)
Private Const DATA_NAME As String = "tachthua_mau22.txt"

' ---- Kich thuoc khung muc 3 trong mau 22 (don vi goc cua file mau) ----
Private Const FR_W As Double = 560435#
Private Const FR_H As Double = 231593#

' ---- Bien dung chung ----
Private nX() As Double, ny() As Double, nCnt As Long
Private chLoops() As Variant, chCnt As Long
Private gS As Double, go As Point3d, gK As Double, gRcx As Double, gRcy As Double

' ====================================================================
'  BUOC 1: CHON THUA SAU TACH
' ====================================================================
Public Sub B1_ChonThua()
    Dim ee As ElementEnumerator, el As Element, pts() As Point3d
    Dim i As Long, k As Long, m As Long, id As Long, c As Long
    Dim ids() As Long, lp As Variant

    nCnt = 0: chCnt = 0
    If Not ActiveModelReference.AnyElementsSelected Then
        MsgBox "Hay chon it nhat 2 thua (shape) sau tach roi chay lai.", vbExclamation
        Exit Sub
    End If

    ' ---- 1. Doc dinh cac thua duoc chon ----
    Set ee = ActiveModelReference.GetSelectedElements
    Do While ee.MoveNext
        Set el = ee.Current
        If GetVerts(el, pts) Then
            ReDim ids(UBound(pts) - LBound(pts))
            m = 0
            For i = LBound(pts) To UBound(pts)
                id = NodeId(pts(i).x, pts(i).y)
                If m = 0 Then
                    ids(0) = id: m = 1
                ElseIf ids(m - 1) <> id Then
                    ids(m) = id: m = m + 1
                End If
            Next
            If m > 1 Then
                If ids(m - 1) = ids(0) Then m = m - 1
            End If
            If m >= 3 Then
                ReDim Preserve ids(m - 1)
                ReDim Preserve chLoops(chCnt)
                chLoops(chCnt) = ids
                chCnt = chCnt + 1
            End If
        End If
    Loop
    If chCnt < 2 Then
        MsgBox "Can chon it nhat 2 thua dang SHAPE kin. Hien chi doc duoc " & chCnt & " thua.", vbExclamation
        Exit Sub
    End If

    ' ---- 2. Chen dinh nam tren canh (diem chia cua thua ben canh) ----
    Dim nL() As Long, nn As Long, a As Long, b As Long
    Dim tt() As Double, tid() As Long, tC As Long, t As Double
    Dim p As Long, q As Long, tmpD As Double, tmpL As Long
    For c = 0 To chCnt - 1
        lp = chLoops(c)
        nn = 0
        ReDim nL(0)
        For i = 0 To UBound(lp)
            a = lp(i): b = lp((i + 1) Mod (UBound(lp) + 1))
            ReDim Preserve nL(nn): nL(nn) = a: nn = nn + 1
            tC = 0
            For k = 0 To nCnt - 1
                If k <> a And k <> b Then
                    If OnSegment(k, a, b, t) Then
                        ReDim Preserve tt(tC): ReDim Preserve tid(tC)
                        tt(tC) = t: tid(tC) = k: tC = tC + 1
                    End If
                End If
            Next
            For p = 0 To tC - 2
                For q = p + 1 To tC - 1
                    If tt(q) < tt(p) Then
                        tmpD = tt(p): tt(p) = tt(q): tt(q) = tmpD
                        tmpL = tid(p): tid(p) = tid(q): tid(q) = tmpL
                    End If
                Next
            Next
            For p = 0 To tC - 1
                ReDim Preserve nL(nn): nL(nn) = tid(p): nn = nn + 1
            Next
        Next
        chLoops(c) = nL
    Next

    ' ---- 3. Dem canh: 1 lan = canh bien, 2 lan = duong chia ----
    Dim dic As Object, kk As Variant, parts() As String
    Set dic = CreateObject("Scripting.Dictionary")
    For c = 0 To chCnt - 1
        lp = chLoops(c)
        For i = 0 To UBound(lp)
            a = lp(i): b = lp((i + 1) Mod (UBound(lp) + 1))
            dic(EK(a, b)) = dic(EK(a, b)) + 1
        Next
    Next

    Dim adj1() As Long, adj2() As Long, deg() As Long, isInner() As Boolean
    ReDim adj1(nCnt - 1): ReDim adj2(nCnt - 1): ReDim deg(nCnt - 1): ReDim isInner(nCnt - 1)
    For i = 0 To nCnt - 1: adj1(i) = -1: adj2(i) = -1: Next
    For Each kk In dic.Keys
        parts = Split(kk, "_")
        a = CLng(parts(0)): b = CLng(parts(1))
        If dic(kk) = 1 Then
            If Not AddAdj(a, b, adj1, adj2, deg) Or Not AddAdj(b, a, adj1, adj2, deg) Then
                MsgBox "Ranh gioi gop bi re nhanh (cac thua chi cham nhau tai 1 diem?).", vbExclamation
                Exit Sub
            End If
        ElseIf dic(kk) = 2 Then
            isInner(a) = True: isInner(b) = True
        Else
            MsgBox "Co canh bi trung tu 3 thua tro len - kiem tra lai cac thua chon (bi chong lan?).", vbExclamation
            Exit Sub
        End If
    Next

    ' ---- 4. Lan theo ranh gioi ngoai ----
    Dim bL() As Long, bn As Long, s As Long, cur As Long, prv As Long, nxt As Long, nb As Long
    s = -1: nb = 0
    For i = 0 To nCnt - 1
        If deg(i) = 2 Then
            nb = nb + 1
            If s < 0 Then s = i
        End If
    Next
    If s < 0 Then MsgBox "Khong tim thay ranh gioi ngoai.", vbExclamation: Exit Sub
    bn = 0: prv = -1: cur = s
    Do
        ReDim Preserve bL(bn): bL(bn) = cur: bn = bn + 1
        If adj1(cur) <> prv Then nxt = adj1(cur) Else nxt = adj2(cur)
        prv = cur: cur = nxt
        If bn > nCnt Then Exit Do
    Loop While cur <> s
    If bn <> nb Then
        MsgBox "Cac thua chon khong lien ke nhau hoac tao lo thung (" & bn & "/" & nb & " dinh).", vbExclamation
        Exit Sub
    End If

    ' chieu kim dong ho
    If LoopArea(bL) > 0 Then ReverseL bL

    ' ---- 5. Dinh cua thua goc (bo diem chia thang hang) ----
    Dim keep() As Boolean
    ReDim keep(bn - 1)
    For i = 0 To bn - 1
        a = bL((i - 1 + bn) Mod bn): b = bL((i + 1) Mod bn)
        keep(i) = Not (isInner(bL(i)) And DistPL(bL(i), a, b) < COL_TOL)
    Next

    ' bat dau tu dinh phia Bac nhat (trung thi lay dinh phia Tay)
    Dim st As Long: st = -1
    For i = 0 To bn - 1
        If keep(i) Then
            If st < 0 Then
                st = i
            ElseIf ny(bL(i)) > ny(bL(st)) + tol Or (Abs(ny(bL(i)) - ny(bL(st))) <= tol And nX(bL(i)) < nX(bL(st))) Then
                st = i
            End If
        End If
    Next
    Dim bl2() As Long, keep2() As Boolean
    ReDim bl2(bn - 1): ReDim keep2(bn - 1)
    For i = 0 To bn - 1
        bl2(i) = bL((st + i) Mod bn): keep2(i) = keep((st + i) Mod bn)
    Next
    bL = bl2: keep = keep2

    ' ---- 6. Danh so ----
    Dim lb() As Long, cnt As Long, nParent As Long, onB() As Boolean
    ReDim lb(nCnt - 1): ReDim onB(nCnt - 1)
    cnt = 0
    For i = 0 To bn - 1
        onB(bL(i)) = True
        If keep(i) Then cnt = cnt + 1: lb(bL(i)) = cnt
    Next
    nParent = cnt
    For i = 0 To bn - 1
        If Not keep(i) Then cnt = cnt + 1: lb(bL(i)) = cnt
    Next
    ' dinh nam ben trong (giao nhieu thua), sap tu Bac xuong Nam
    Dim inn() As Long, ni As Long
    ni = 0
    For i = 0 To nCnt - 1
        If Not onB(i) Then ReDim Preserve inn(ni): inn(ni) = i: ni = ni + 1
    Next
    For p = 0 To ni - 2
        For q = p + 1 To ni - 1
            If ny(inn(q)) > ny(inn(p)) Then tmpL = inn(p): inn(p) = inn(q): inn(q) = tmpL
        Next
    Next
    For p = 0 To ni - 1
        cnt = cnt + 1: lb(inn(p)) = cnt
    Next

    ' ---- 7. Danh sach canh sau tach ----
    Dim eA() As Long, eB() As Long, nE As Long
    nE = 0
    For i = 0 To bn - 1
        ReDim Preserve eA(nE): ReDim Preserve eB(nE)
        eA(nE) = bL(i): eB(nE) = bL((i + 1) Mod bn): nE = nE + 1
    Next
    Dim ie0 As Long: ie0 = nE
    For Each kk In dic.Keys
        If dic(kk) = 2 Then
            parts = Split(kk, "_")
            a = CLng(parts(0)): b = CLng(parts(1))
            If lb(b) < lb(a) Then tmpL = a: a = b: b = tmpL
            ReDim Preserve eA(nE): ReDim Preserve eB(nE)
            eA(nE) = a: eB(nE) = b: nE = nE + 1
        End If
    Next
    For p = ie0 To nE - 2
        For q = p + 1 To nE - 1
            If lb(eA(q)) < lb(eA(p)) Or (lb(eA(q)) = lb(eA(p)) And lb(eB(q)) < lb(eB(p))) Then
                tmpL = eA(p): eA(p) = eA(q): eA(q) = tmpL
                tmpL = eB(p): eB(p) = eB(q): eB(q) = tmpL
            End If
        Next
    Next

    ' ---- 8. Dien tich, trong tam; sap thua con tu Bac xuong Nam ----
    Dim ca() As Double, cx() As Double, cy() As Double, ord() As Long, lpL() As Long
    ReDim ca(chCnt - 1): ReDim cx(chCnt - 1): ReDim cy(chCnt - 1): ReDim ord(chCnt - 1)
    For c = 0 To chCnt - 1
        lpL = chLoops(c)
        ca(c) = Abs(LoopArea(lpL))
        LoopCentroid lpL, cx(c), cy(c)
        ord(c) = c
    Next
    For p = 0 To chCnt - 2
        For q = p + 1 To chCnt - 1
            If cy(ord(q)) > cy(ord(p)) Then tmpL = ord(p): ord(p) = ord(q): ord(q) = tmpL
        Next
    Next
    Dim pv() As Long, nP As Long, pA As Double, pcx As Double, pcy As Double, sumA As Double
    nP = 0
    For i = 0 To bn - 1
        If keep(i) Then ReDim Preserve pv(nP): pv(nP) = bL(i): nP = nP + 1
    Next
    pA = Abs(LoopArea(pv))
    LoopCentroid pv, pcx, pcy
    sumA = 0
    For c = 0 To chCnt - 1: sumA = sumA + RoundN(ca(c), 1): Next

    ' ---- 9. Hoi so thua, loai dat ----
    Dim soG As String, ldG As String, sNames As String, sLD As String
    Dim arN() As String, arL() As String
    GuessLabels bL, soG, ldG
    soG = InputBox("So thua GOC:", "Mau 22 - Tach thua", soG)
    If soG = "" Then Exit Sub
    ldG = InputBox("Loai dat thua GOC:", "Mau 22 - Tach thua", IIf(ldG = "", "LUK", ldG))
    sNames = "": sLD = ""
    For c = 0 To chCnt - 1
        sNames = sNames & IIf(c > 0, ",", "") & soG & "-" & (c + 1)
        sLD = sLD & IIf(c > 0, ",", "") & ldG
    Next
    sNames = InputBox("So hieu cac thua SAU TACH, thu tu tu BAC xuong NAM, cach nhau dau phay:", "Mau 22 - Tach thua", sNames)
    sLD = InputBox("Loai dat cac thua SAU TACH (cung thu tu), cach nhau dau phay:", "Mau 22 - Tach thua", sLD)
    arN = Split(sNames, ","): arL = Split(sLD, ",")

    ' ---- 10. Ghi file tam ----
    Dim f As Integer, nm As String, ld As String
    f = FreeFile
    Open DataPath() For Output As #f
    Print #f, "G" & vbTab & soG & vbTab & ldG & vbTab & Str(pA) & vbTab & Str(pcx) & vbTab & Str(pcy)
    For i = 0 To nP - 1
        Print #f, "P" & vbTab & Str(nX(pv(i))) & vbTab & Str(ny(pv(i))) & vbTab & CStr(lb(pv(i)))
    Next
    For i = 0 To bn - 1
        Print #f, "B" & vbTab & Str(nX(bL(i))) & vbTab & Str(ny(bL(i))) & vbTab & CStr(lb(bL(i))) & "'"
    Next
    For i = 0 To ni - 1
        Print #f, "I" & vbTab & Str(nX(inn(i))) & vbTab & Str(ny(inn(i))) & vbTab & CStr(lb(inn(i))) & "'"
    Next
    For p = 0 To chCnt - 1
        c = ord(p)
        If p <= UBound(arN) Then nm = Trim$(arN(p)) Else nm = soG & "-" & (p + 1)
        If p <= UBound(arL) Then ld = Trim$(arL(p)) Else ld = ldG
        lpL = chLoops(c)
        Print #f, "C" & vbTab & nm & vbTab & ld & vbTab & Str(ca(c)) & vbTab & Str(cx(c)) & vbTab & Str(cy(c)) & vbTab & CStr(UBound(lpL) + 1)
        For i = 0 To UBound(lpL)
            Print #f, "V" & vbTab & Str(nX(lpL(i))) & vbTab & Str(ny(lpL(i)))
        Next
    Next
    For i = 0 To nE - 1
        Print #f, "E" & vbTab & lb(eA(i)) & "'" & vbTab & lb(eB(i)) & "'" & vbTab & Str(Dist(eA(i), eB(i)))
    Next
    Close #f

    Dim msg As String
    msg = "Da doc " & chCnt & " thua sau tach." & vbCrLf & _
          "Thua goc " & soG & ": " & nParent & " dinh, dien tich " & FmtN(pA, 1) & " m2" & vbCrLf & _
          "Tong dien tich thua sau tach: " & FmtN(sumA, 1) & " m2"
    If Abs(RoundN(pA, 1) - sumA) > 0.05 Then msg = msg & vbCrLf & "(Lech do lam tron: " & FmtN(RoundN(pA, 1) - sumA, 1) & " m2)"
    msg = msg & vbCrLf & "So canh sau tach: " & nE & vbCrLf & vbCrLf & _
          "Bay gio mo file MAU 22 va chay B2_VeSoDo."
    MsgBox msg, vbInformation, "Mau 22 - Buoc 1 xong"
End Sub

' ====================================================================
'  BUOC 2: VE VAO MAU 22
' ====================================================================
Public Sub B2_VeSoDo()
    Dim f As Integer, ln As String, a() As String
    Dim gSo As String, gLd As String, gA As Double, gcx As Double, gcy As Double
    Dim px() As Double, py() As Double, pl() As String, nP As Long
    Dim bx() As Double, by() As Double, bL() As String, nb As Long
    Dim ix() As Double, iy() As Double, iL() As String, ni As Long
    Dim cN() As String, cL() As String, ca() As Double, ccx() As Double, ccy() As Double, cs() As Long, cE() As Long, nC As Long
    Dim vx() As Double, vy() As Double, nV As Long
    Dim e1() As String, e2() As String, el() As Double, nE As Long

    If Dir(DataPath()) = "" Then
        MsgBox "Chua co du lieu. Hay chay B1_ChonThua o file ban do truoc.", vbExclamation
        Exit Sub
    End If
    f = FreeFile
    Open DataPath() For Input As #f
    Do While Not EOF(f)
        Line Input #f, ln
        a = Split(ln, vbTab)
        If UBound(a) >= 0 Then
            Select Case a(0)
            Case "G": gSo = a(1): gLd = a(2): gA = val(a(3)): gcx = val(a(4)): gcy = val(a(5))
            Case "P"
                ReDim Preserve px(nP): ReDim Preserve py(nP): ReDim Preserve pl(nP)
                px(nP) = val(a(1)): py(nP) = val(a(2)): pl(nP) = a(3): nP = nP + 1
            Case "B"
                ReDim Preserve bx(nb): ReDim Preserve by(nb): ReDim Preserve bL(nb)
                bx(nb) = val(a(1)): by(nb) = val(a(2)): bL(nb) = a(3): nb = nb + 1
            Case "I"
                ReDim Preserve ix(ni): ReDim Preserve iy(ni): ReDim Preserve iL(ni)
                ix(ni) = val(a(1)): iy(ni) = val(a(2)): iL(ni) = a(3): ni = ni + 1
            Case "C"
                ReDim Preserve cN(nC): ReDim Preserve cL(nC): ReDim Preserve ca(nC)
                ReDim Preserve ccx(nC): ReDim Preserve ccy(nC): ReDim Preserve cs(nC): ReDim Preserve cE(nC)
                cN(nC) = a(1): cL(nC) = a(2): ca(nC) = val(a(3)): ccx(nC) = val(a(4)): ccy(nC) = val(a(5))
                cs(nC) = nV: cE(nC) = nV + CLng(a(6)) - 1: nC = nC + 1
            Case "V"
                ReDim Preserve vx(nV): ReDim Preserve vy(nV)
                vx(nV) = val(a(1)): vy(nV) = val(a(2)): nV = nV + 1
            Case "E"
                ReDim Preserve e1(nE): ReDim Preserve e2(nE): ReDim Preserve el(nE)
                e1(nE) = a(1): e2(nE) = a(2): el(nE) = val(a(3)): nE = nE + 1
            End Select
        End If
    Loop
    Close #f
    If nP < 3 Or nC < 2 Then MsgBox "File du lieu khong hop le.", vbExclamation: Exit Sub

    ' ---- Lay 2 goc khung muc 3 ----
    Dim p1 As Point3d, p2 As Point3d
    If Not GetPoint("Bam goc DUOI-TRAI khung muc 3 (khung chua 3.1, 3.2, 3.3)", p1) Then Exit Sub
    If Not GetPoint("Bam goc TREN-PHAI khung muc 3", p2) Then Exit Sub
    go = Point3dFromXY(IIf(p1.x < p2.x, p1.x, p2.x), IIf(p1.y < p2.y, p1.y, p2.y))
    gS = Abs(p2.x - p1.x) / FR_W
    If gS <= 0 Then Exit Sub
    If Abs(Abs(p2.y - p1.y) / FR_H - gS) / gS > 0.05 Then
        If MsgBox("Ti le khung bam khong khop mau 22. Van tiep tuc?", vbYesNo + vbQuestion) = vbNo Then Exit Sub
    End If

    ' luu cai dat chu
    Dim oH As Double, oW As Double, oJ As MsdTextJustification
    oH = ActiveSettings.TextStyle.Height: oW = ActiveSettings.TextStyle.Width
    oJ = ActiveSettings.TextStyle.Justification

    ' ---- Ti le so do: vua o 3.1 va 3.2 ----
    Const AW As Double = 176000#, AH As Double = 175000#
    Const C31X As Double = 100348#, C32X As Double = 306903#, cy As Double = 100000#
    Dim i As Long, j As Long, mnx As Double, mxx As Double, mny As Double, mxy As Double
    mnx = px(0): mxx = px(0): mny = py(0): mxy = py(0)
    For i = 0 To nP - 1
        If px(i) < mnx Then mnx = px(i)
        If px(i) > mxx Then mxx = px(i)
        If py(i) < mny Then mny = py(i)
        If py(i) > mxy Then mxy = py(i)
    Next
    gRcx = (mnx + mxx) / 2: gRcy = (mny + mxy) / 2
    gK = AW / IIf(mxx - mnx > 0.001, mxx - mnx, 0.001)
    If AH / IIf(mxy - mny > 0.001, mxy - mny, 0.001) < gK Then gK = AH / IIf(mxy - mny > 0.001, mxy - mny, 0.001)
    gK = gK * 0.72

    Dim TH As Double, OFF As Double: TH = 5000#: OFF = 7000#
    Dim v() As Point3d, ux As Double, uy As Double

    ' ---- 3.1 SO DO TRUOC TACH ----
    ReDim v(nP)
    For i = 0 To nP - 1: v(i) = mp(px(i), py(i), C31X, cy): Next
    v(nP) = v(0)
    AddShape v
    For i = 0 To nP - 1
        Bisector px((i - 1 + nP) Mod nP), py((i - 1 + nP) Mod nP), px(i), py(i), px((i + 1) Mod nP), py((i + 1) Mod nP), ux, uy
        PutText pl(i), RelOff(v(i), ux * OFF, uy * OFF), TH * 0.9, msdTextJustificationCenterCenter
    Next
    PutFraction gLd, gSo, FmtN(gA, 1), mp(gcx, gcy, C31X, cy), TH

    ' ---- 3.2 SO DO SAU TACH ----
    Dim c As Long, k As Long
    For c = 0 To nC - 1
        ReDim v(cE(c) - cs(c) + 1)
        k = 0
        For j = cs(c) To cE(c): v(k) = mp(vx(j), vy(j), C32X, cy): k = k + 1: Next
        v(k) = v(0)
        AddShape v
        PutFraction cL(c), cN(c), FmtN(ca(c), 1), mp(ccx(c), ccy(c), C32X, cy), TH
    Next
    For i = 0 To nb - 1
        Bisector bx((i - 1 + nb) Mod nb), by((i - 1 + nb) Mod nb), bx(i), by(i), bx((i + 1) Mod nb), by((i + 1) Mod nb), ux, uy
        PutText bL(i), RelOff(mp(bx(i), by(i), C32X, cy), ux * OFF, uy * OFF), TH * 0.9, msdTextJustificationCenterCenter
    Next
    For i = 0 To ni - 1
        PutText iL(i), RelOff(mp(ix(i), iy(i), C32X, cy), OFF * 0.7, OFF * 0.7), TH * 0.9, msdTextJustificationCenterCenter
    Next

    ' ---- 3.3 BANG DO DAI CANH (2 cot x 10 dong) ----
    Dim rTop As Variant, colD As Variant, coll As Variant, rc As Double, over As String
    rTop = Array(176985#, 159281#, 141277#, 123712#, 105708#, 87865#, 69861#, 52297#, 34293#, 16975#, 0#)
    colD = Array(442292#, 508692#)
    coll = Array(475492#, 541926#)
    over = ""
    For i = 0 To nE - 1
        c = i \ 10: j = i Mod 10
        If c <= 1 Then
            rc = (rTop(j) + rTop(j + 1)) / 2
            PutText e1(i) & " - " & e2(i), sp(CDbl(colD(c)), rc), TH * 0.9, msdTextJustificationCenterCenter
            PutText FmtN(el(i), 2), sp(CDbl(coll(c)), rc), TH * 0.9, msdTextJustificationCenterCenter
        Else
            over = over & e1(i) & " - " & e2(i) & " : " & FmtN(el(i), 2) & vbCrLf
        End If
    Next

    ActiveSettings.TextStyle.Height = oH: ActiveSettings.TextStyle.Width = oW
    ActiveSettings.TextStyle.Justification = oJ

    If over <> "" Then
        MsgBox "Bang 3.3 chi co 20 o. Cac canh con lai can ghi them:" & vbCrLf & over, vbExclamation
    Else
        MsgBox "Da ve xong so do 3.1, 3.2 va bang 3.3." & vbCrLf & _
               "Ten chu su dung giap ranh va vi tri nhan co the chinh tay neu can.", vbInformation
    End If
End Sub

' ====================================================================
'  HAM PHU
' ====================================================================
Private Function DataPath() As String
    Dim t As String
    t = Environ$("TEMP")
    If t = "" Then t = "C:"
    If Right$(t, 1) = "\" Then t = Left$(t, Len(t) - 1)
    DataPath = t & "\" & DATA_NAME
End Function

Private Function NodeId(ByVal x As Double, ByVal y As Double) As Long
    Dim i As Long
    For i = 0 To nCnt - 1
        If Abs(nX(i) - x) < tol And Abs(ny(i) - y) < tol Then NodeId = i: Exit Function
    Next
    ReDim Preserve nX(nCnt): ReDim Preserve ny(nCnt)
    nX(nCnt) = x: ny(nCnt) = y
    NodeId = nCnt
    nCnt = nCnt + 1
End Function

Private Function GetVerts(el As Element, pts() As Point3d) As Boolean
    Dim ee As ElementEnumerator, sb As Element, v() As Point3d, i As Long, n As Long
    On Error GoTo Fail
    If el.IsShapeElement Then
        pts = el.AsShapeElement.GetVertices
        GetVerts = True
        Exit Function
    End If
    If el.Type = msdElementTypeComplexShape Then
        n = 0
        Set ee = el.AsComplexShapeElement.GetSubElements
        Do While ee.MoveNext
            Set sb = ee.Current
            v = sb.AsVertexList.GetVertices
            For i = LBound(v) To UBound(v)
                ReDim Preserve pts(n)
                pts(n) = v(i): n = n + 1
            Next
        Loop
        GetVerts = (n >= 3)
        Exit Function
    End If
Fail:
    GetVerts = False
End Function

Private Function EK(ByVal a As Long, ByVal b As Long) As String
    If a < b Then EK = a & "_" & b Else EK = b & "_" & a
End Function

Private Function AddAdj(ByVal a As Long, ByVal b As Long, adj1() As Long, adj2() As Long, deg() As Long) As Boolean
    If deg(a) = 0 Then
        adj1(a) = b
    ElseIf deg(a) = 1 Then
        adj2(a) = b
    Else
        AddAdj = False: Exit Function
    End If
    deg(a) = deg(a) + 1
    AddAdj = True
End Function

Private Function OnSegment(ByVal k As Long, ByVal a As Long, ByVal b As Long, t As Double) As Boolean
    Dim dx As Double, dy As Double, L2 As Double, cr As Double
    dx = nX(b) - nX(a): dy = ny(b) - ny(a)
    L2 = dx * dx + dy * dy
    If L2 < 0.000001 Then Exit Function
    t = ((nX(k) - nX(a)) * dx + (ny(k) - ny(a)) * dy) / L2
    If t <= 0.000001 Or t >= 0.999999 Then Exit Function
    cr = (nX(k) - nX(a)) * dy - (ny(k) - ny(a)) * dx
    OnSegment = (Abs(cr) / Sqr(L2) < tol)
End Function

Private Function DistPL(ByVal k As Long, ByVal a As Long, ByVal b As Long) As Double
    Dim dx As Double, dy As Double, L As Double
    dx = nX(b) - nX(a): dy = ny(b) - ny(a)
    L = Sqr(dx * dx + dy * dy)
    If L < 0.000001 Then DistPL = 1E+20: Exit Function
    DistPL = Abs((nX(k) - nX(a)) * dy - (ny(k) - ny(a)) * dx) / L
End Function

Private Function Dist(ByVal a As Long, ByVal b As Long) As Double
    Dist = Sqr((nX(b) - nX(a)) ^ 2 + (ny(b) - ny(a)) ^ 2)
End Function

Private Function LoopArea(lp() As Long) As Double
    Dim i As Long, n As Long, s As Double, a As Long, b As Long
    n = UBound(lp) + 1
    For i = 0 To n - 1
        a = lp(i): b = lp((i + 1) Mod n)
        s = s + (nX(a) - nX(lp(0))) * (ny(b) - ny(lp(0))) - (nX(b) - nX(lp(0))) * (ny(a) - ny(lp(0)))
    Next
    LoopArea = s / 2
End Function

Private Sub LoopCentroid(lp() As Long, cx As Double, cy As Double)
    Dim i As Long, n As Long, a As Long, b As Long, cr As Double, s As Double
    Dim X0 As Double, Y0 As Double, xa As Double, ya As Double, xb As Double, yB As Double
    n = UBound(lp) + 1
    X0 = nX(lp(0)): Y0 = ny(lp(0))
    cx = 0: cy = 0: s = 0
    For i = 0 To n - 1
        a = lp(i): b = lp((i + 1) Mod n)
        xa = nX(a) - X0: ya = ny(a) - Y0: xb = nX(b) - X0: yB = ny(b) - Y0
        cr = xa * yB - xb * ya
        s = s + cr
        cx = cx + (xa + xb) * cr: cy = cy + (ya + yB) * cr
    Next
    If Abs(s) < 0.000001 Then
        cx = X0: cy = Y0
    Else
        cx = cx / (3 * s) + X0: cy = cy / (3 * s) + Y0
    End If
End Sub

Private Sub ReverseL(lp() As Long)
    Dim i As Long, n As Long, t As Long
    n = UBound(lp)
    For i = 0 To (n - 1) \ 2
        t = lp(i): lp(i) = lp(n - i): lp(n - i) = t
    Next
End Sub

Private Function PtInLoop(ByVal x As Double, ByVal y As Double, lp() As Long) As Boolean
    Dim i As Long, j As Long, n As Long, ins As Boolean
    n = UBound(lp) + 1: j = n - 1
    For i = 0 To n - 1
        If ((ny(lp(i)) > y) <> (ny(lp(j)) > y)) Then
            If x < (nX(lp(j)) - nX(lp(i))) * (y - ny(lp(i))) / (ny(lp(j)) - ny(lp(i))) + nX(lp(i)) Then ins = Not ins
        End If
        j = i
    Next
    PtInLoop = ins
End Function

Private Sub GuessLabels(lp() As Long, so As String, ld As String)
    Dim sc As New ElementScanCriteria, ee As ElementEnumerator, el As Element
    Dim s As String, h As Double, hSo As Double, hLd As Double, o As Point3d
    On Error Resume Next
    sc.ExcludeAllTypes
    sc.IncludeType msdElementTypeText
    Set ee = ActiveModelReference.Scan(sc)
    Do While ee.MoveNext
        Set el = ee.Current
        s = Trim$(el.AsTextElement.Text)
        o = el.AsTextElement.Origin
        h = el.AsTextElement.TextStyle.Height
        If PtInLoop(o.x, o.y, lp) Then
            If IsAllDigits(s) And h > hSo Then so = s: hSo = h
            If IsLoaiDat(s) And h > hLd Then ld = s: hLd = h
        End If
    Loop
End Sub

Private Function IsAllDigits(s As String) As Boolean
    Dim i As Long
    If Len(s) = 0 Then Exit Function
    For i = 1 To Len(s)
        If Mid$(s, i, 1) < "0" Or Mid$(s, i, 1) > "9" Then Exit Function
    Next
    IsAllDigits = True
End Function

Private Function IsLoaiDat(s As String) As Boolean
    Dim i As Long
    If Len(s) < 2 Or Len(s) > 4 Then Exit Function
    For i = 1 To Len(s)
        If Mid$(s, i, 1) < "A" Or Mid$(s, i, 1) > "Z" Then Exit Function
    Next
    IsLoaiDat = True
End Function

Private Function RoundN(ByVal x As Double, ByVal d As Integer) As Double
    RoundN = Int(x * 10 ^ d + 0.5) / 10 ^ d
End Function

Private Function FmtN(ByVal x As Double, ByVal d As Integer) As String
    Dim s As String
    If d = 1 Then s = Format$(RoundN(x, 1), "0.0") Else s = Format$(RoundN(x, 2), "0.00")
    FmtN = Replace(s, ".", ",")
End Function

Private Function sp(ByVal rx As Double, ByVal ry As Double) As Point3d
    sp = Point3dFromXY(go.x + rx * gS, go.y + ry * gS)
End Function

Private Function mp(ByVal x As Double, ByVal y As Double, ByVal bcx As Double, ByVal bcy As Double) As Point3d
    mp = sp(bcx + (x - gRcx) * gK, bcy + (y - gRcy) * gK)
End Function

Private Function RelOff(p As Point3d, ByVal dx As Double, ByVal dy As Double) As Point3d
    RelOff = Point3dFromXY(p.x + dx * gS, p.y + dy * gS)
End Function

Private Sub Bisector(ByVal ax As Double, ByVal ay As Double, ByVal vx As Double, ByVal vy As Double, _
                     ByVal bx As Double, ByVal by As Double, ux As Double, uy As Double)
    Dim d1x As Double, d1y As Double, d2x As Double, d2y As Double, L As Double
    d1x = vx - ax: d1y = vy - ay: L = Sqr(d1x * d1x + d1y * d1y): If L > 0 Then d1x = d1x / L: d1y = d1y / L
    d2x = bx - vx: d2y = by - vy: L = Sqr(d2x * d2x + d2y * d2y): If L > 0 Then d2x = d2x / L: d2y = d2y / L
    ' vong theo chieu kim dong ho: phap tuyen ngoai = (-dy, dx)
    ux = -d1y - d2y: uy = d1x + d2x
    L = Sqr(ux * ux + uy * uy)
    If L < 0.000001 Then
        ux = -d1y: uy = d1x
    Else
        ux = ux / L: uy = uy / L
    End If
End Sub

Private Sub AddShape(v() As Point3d)
    Dim el As ShapeElement
    Set el = CreateShapeElement1(Nothing, v, msdFillModeNotFilled)
    ActiveModelReference.AddElement el
End Sub

Private Sub AddLine(p1 As Point3d, p2 As Point3d)
    Dim el As LineElement
    Set el = CreateLineElement2(Nothing, p1, p2)
    ActiveModelReference.AddElement el
End Sub

Private Sub PutText(ByVal s As String, p As Point3d, ByVal relH As Double, ByVal just As MsdTextJustification)
    Dim t As TextElement, h As Double
    h = relH * gS
    ActiveSettings.TextStyle.Height = h
    ActiveSettings.TextStyle.Width = h
    ActiveSettings.TextStyle.Justification = just
    Set t = CreateTextElement1(Nothing, s, p, Matrix3dIdentity)
    t.TextStyle.Height = h
    t.TextStyle.Width = h
    ActiveModelReference.AddElement t
End Sub

Private Sub PutFraction(ByVal ld As String, ByVal so As String, ByVal dt As String, c As Point3d, ByVal TH As Double)
    Dim w As Double, L As Long
    L = Len(so): If Len(dt) > L Then L = Len(dt)
    w = L * TH * 0.75
    PutText so, RelOff(c, 0, TH * 0.65), TH, msdTextJustificationCenterCenter
    PutText dt, RelOff(c, 0, -TH * 0.65), TH, msdTextJustificationCenterCenter
    AddLine RelOff(c, -w / 2, 0), RelOff(c, w / 2, 0)
    PutText ld, RelOff(c, -w / 2 - TH * 0.3, 0), TH, msdTextJustificationRightCenter
End Sub

Private Function GetPoint(ByVal prompt As String, pt As Point3d) As Boolean
    Dim msg As CadInputMessage
    ShowPrompt prompt
    Do
        Set msg = CadInputQueue.GetInput(msdCadInputTypeDataPoint, msdCadInputTypeReset)
        If msg.InputType = msdCadInputTypeDataPoint Then
            pt = msg.Point
            GetPoint = True
            Exit Do
        ElseIf msg.InputType = msdCadInputTypeReset Then
            GetPoint = False
            Exit Do
        End If
    Loop
    ShowPrompt ""
End Function

Attribute VB_Name = "clsChonThuaTL"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'============================================================
' clsChonThuaTL - Bam vao 1 thua tren ban do -> xuat trich luc thua do.
'   Reset (chuot phai) = thoi. Prompt de ASCII (thanh trang thai).
'   Can: IPrimitiveCommandEvents, TimThuaChua, ChayTrichLucThua.
'   Chi can co vung topology (CSDL) - thua chua gan so van xuat duoc.
'============================================================
Option Explicit
Implements IPrimitiveCommandEvents

Public vungs As Collection
Public csdl As String, mau As String, kieu As String, toBanDo As String
Public xa As String, huyen As String, tinh As String, lvXuat As String
Public cao As Double, cheDoMau As Boolean, tyLe As Double
' SUA 11/10/2026: 0 = trich luc, 1 = tach thua, 2 = hop thua (bam nhieu thua, Reset = xong)
Public cheDo As Long, ini As String, lvCat As String
Private mXong As Boolean
Private mDs As New Collection

Private mTec As New Collection   ' to sang cac thua da chon

Private Sub IPrimitiveCommandEvents_Start()
    On Error Resume Next
    ShowCommand "Trich luc - chon thua"
    Select Case cheDo
        Case 1: ShowPrompt "TACH: bam cac thua con (vd 17, 78) hoac 1 thua da ve duong cat ; bam lai thua da chon / Reset = xong"
        Case 2: ShowPrompt "HOP: bam lan luot cac thua can hop ; bam lai thua da chon / Reset = xong"
        Case Else: ShowPrompt "Bam vao TRONG thua can trich luc ; Reset (chuot phai) = thoi"
    End Select
End Sub

Private Sub IPrimitiveCommandEvents_Datapoint(pt As Point3d, ByVal oView As View)
    Dim v As clsVung
    On Error Resume Next
    Set v = TimThuaChua(vungs, pt.x, pt.y)
    On Error GoTo 0
    If v Is Nothing Then
        ShowPrompt "Khong co thua (trong CSDL) tai day - bam cho khac ; Reset = thoi"
        Exit Sub
    End If
    Set gViewTL = oView
    If cheDo = 1 Or cheDo = 2 Then
        ' bam lai thua da chon (double click) = xong
        Dim i As Long
        For i = 1 To mDs.Count
            If mDs.Item(i) Is v Then XongChon: Exit Sub
        Next i
        mDs.Add v
        ToSang v
        ShowPrompt "Da chon " & mDs.Count & " thua (" & dsSo() & ") ; bam thua tiep ; bam lai thua da chon / Reset = xong"
        Exit Sub
    End If
    ' Thua chua gan thong tin van xuat: so thua 0, loai dat 0, dien tich tu tinh
    mXong = True
    CommandState.StartDefaultCommand
    ChayTrichLucThua v, mau, kieu, toBanDo, xa, huyen, tinh, _
                     lvXuat, cao, cheDoMau, tyLe
    MoLaiForm Trim$(v.soThua)
End Sub

' Ket thuc chon (tach / hop)
Private Sub XongChon()
    Dim dS As String
    mXong = True
    TatSang
    CommandState.StartDefaultCommand
    dS = dsSo()
    If cheDo = 1 And mDs.Count >= 1 Then
        DC_ChayTachHop 1, mDs, mau, ini, toBanDo, xa, huyen, tinh, tyLe, lvCat
    ElseIf cheDo = 2 And mDs.Count >= 2 Then
        DC_ChayTachHop 2, mDs, mau, ini, toBanDo, xa, huyen, tinh, tyLe, ""
    End If
    MoLaiForm dS
End Sub

' To sang ranh thua vua chon (phan tu tam, khong ghi vao ban ve)
Private Sub ToSang(ByVal v As clsVung)
    Dim rg() As Double, pts() As Point3d, i As Long, n As Long, el As Element, tec As Object
    On Error Resume Next
    rg = v.ring: n = UBound(rg, 1)
    ReDim pts(0 To n)
    For i = 0 To n
        pts(i).x = rg(i, 0): pts(i).y = rg(i, 1): pts(i).Z = 0#
    Next i
    Set el = CreateShapeElement1(Nothing, pts)
    If el Is Nothing Then Exit Sub
    el.LineWeight = 4
    Set tec = CreateTransientElementContainer1(el, 0, 255, msdDrawingModeHilite)
    If Not tec Is Nothing Then mTec.Add tec
End Sub

Private Sub TatSang()
    Dim i As Long
    On Error Resume Next
    For i = mTec.Count To 1 Step -1
        mTec.Item(i).Reset
        mTec.Remove i
    Next i
End Sub
Private Sub IPrimitiveCommandEvents_Dynamics(pt As Point3d, ByVal oView As View, ByVal DrawMode As MsdDrawingMode)
End Sub

Private Sub IPrimitiveCommandEvents_Keyin(ByVal keyin As String)
End Sub

Private Sub IPrimitiveCommandEvents_Reset()
    If (cheDo = 1 And mDs.Count >= 1) Or (cheDo = 2 And mDs.Count >= 2) Then XongChon: Exit Sub
    mXong = True
    TatSang
    CommandState.StartDefaultCommand
    MoLaiForm ""
End Sub

Private Function dsSo() As String
    Dim i As Long
    For i = 1 To mDs.Count
        If i > 1 Then dsSo = dsSo & "+"
        dsSo = dsSo & Trim$(mDs.Item(i).soThua)
    Next i
End Function

Private Sub IPrimitiveCommandEvents_Cleanup()
    ' bi cong cu khac thay the khi chua chon -> mo lai form
    TatSang
    If Not mXong Then
        mXong = True
        MoLaiForm ""
    End If
End Sub

Private Sub MoLaiForm(ByVal soThua As String)
    On Error Resume Next
    frmTrichLuc.Show vbModeless
    If Len(soThua) > 0 Then frmTrichLuc.Controls("txtSoThua").Text = soThua
End Sub

Attribute VB_Name = "clsComboEvent"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public WithEvents cbo As MSForms.ComboBox
Attribute cbo.VB_VarHelpID = -1
Public Form As Object
Public ma As String          ' "" = combo Tinh ; "MAUHS" = combo Mau ho so

Private Sub cbo_Change()
    If Form Is Nothing Then Exit Sub
    If ma = "MAUHS" Then Form.MauHSDoi Else Form.TinhDoi
End Sub

Attribute VB_Name = "clsCuonList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' Bat MouseMove tren ListBox -> bat cuon chuot (modCuonChuot)
Public WithEvents lst As MSForms.ListBox
Attribute lst.VB_VarHelpID = -1
Public Form As Object

Private Sub lst_MouseMove(ByVal Button As Integer, ByVal Shift As Integer, ByVal x As Single, ByVal y As Single)
    DC_CuonBat lst, Form
End Sub

Attribute VB_Name = "clsListEvent"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' Bat su kien bam dong trong ListBox -> goi Form.DongChon
Public WithEvents lst As MSForms.ListBox
Attribute lst.VB_VarHelpID = -1
Public Form As Object

Private Sub lst_Click()
    If Not Form Is Nothing Then Form.DongChon
End Sub

Attribute VB_Name = "clsMenuTop"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'============================================================
' clsMenuTop - bat su kien cho 1 nhan tren thanh menu (frmDiaChinh)
'============================================================
Option Explicit

Public WithEvents lbl As MSForms.Label
Attribute lbl.VB_VarHelpID = -1
Public Form As Object
Public ma As String

Private Sub lbl_MouseDown(ByVal Button As Integer, ByVal Shift As Integer, ByVal x As Single, ByVal y As Single)
    On Error GoTo Loi
    If Button = 1 Then
        If Not Form Is Nothing Then Form.MoMenuTop ma, lbl, x, y
    End If
    Exit Sub
Loi:
    MsgBox "LOI menu '" & ma & "'" & vbCrLf & _
           "So loi : " & Err.Number & vbCrLf & _
           "Mo ta  : " & Err.Description, vbCritical, "Bat loi"
End Sub

Private Sub lbl_MouseMove(ByVal Button As Integer, ByVal Shift As Integer, ByVal x As Single, ByVal y As Single)
    On Error Resume Next
    If Not Form Is Nothing Then Form.HoverTop ma
End Sub

Attribute VB_Name = "clsNhanBam"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' Bam vao Label (vd tieu de cot) -> goi Form.XuLyNut ma
Public WithEvents lbl As MSForms.Label
Attribute lbl.VB_VarHelpID = -1
Public Form As Object
Public ma As String

Private Sub lbl_Click()
    If Not Form Is Nothing Then Form.XuLyNut ma
End Sub

Attribute VB_Name = "clsNutTL"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public WithEvents btn As MSForms.CommandButton
Attribute btn.VB_VarHelpID = -1
Public Form As Object
Public ma As String

Private Sub btn_Click()
    On Error GoTo Loi
    If Not Form Is Nothing Then Form.XuLyNut ma
    Exit Sub
Loi:
    MsgBox "LOI khi chay '" & ma & "'" & vbCrLf & vbCrLf & _
           "So loi : " & Err.Number & vbCrLf & _
           "Mo ta  : " & Err.Description & vbCrLf & _
           "Nguon  : " & Err.Source, _
           vbCritical, "Bat loi"
End Sub

Attribute VB_Name = "clsTaoVungDiem"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'============================================================
' clsTaoVungDiem - Tao vung theo DIEM BAM (kieu Create Region/Flood).
'   Bam vao trong thua -> tao tam thua do ; Reset (chuot phai) = ket thuc.
'   Can: IPrimitiveCommandEvents (MicroStationDGN), TimThuaChua, VeTam, LuuCSDL.
'   Prompt/MsgBox de ASCII (thanh trang thai khong ve duoc chu Viet mo rong).
'============================================================
Option Explicit
Implements IPrimitiveCommandEvents

Public vungs As Collection
Public loaiDat As String
Public toBanDo As String
Public kt As Double
Public mauTam As Long
Public csdlPath As String
Private demChon As Long
Private daKetThuc As Boolean

Private Sub IPrimitiveCommandEvents_Start()
    On Error Resume Next
    ShowCommand "Tao vung theo diem"
    ShowPrompt "Bam vao trong thua de tao tam ; Reset (chuot phai) = ket thuc"
    On Error GoTo 0
End Sub

Private Sub IPrimitiveCommandEvents_Datapoint(pt As Point3d, ByVal oView As View)
    On Error Resume Next
    Dim v As clsVung
    Set v = TimThuaChua(vungs, pt.x, pt.y)
    If v Is Nothing Then
        ShowPrompt "Khong co thua khep kin tai day - bam cho khac."
        Exit Sub
    End If
    If v.daChon Then
        ShowPrompt "Thua nay da tao roi - bam thua khac."
        Exit Sub
    End If
    v.daChon = True
    If Len(v.loaiDat) = 0 Then v.loaiDat = loaiDat
    If Len(v.SoTo) = 0 Then v.SoTo = toBanDo
    VeTamHong v.cx, v.cy, kt, mauTam
    demChon = demChon + 1
    ShowPrompt "Da tao " & demChon & " thua. Bam tiep hoac Reset de ket thuc."
    On Error GoTo 0
End Sub

Private Sub IPrimitiveCommandEvents_Dynamics(pt As Point3d, ByVal oView As View, ByVal DrawMode As MsdDrawingMode)
    ' khong dung
End Sub

Private Sub IPrimitiveCommandEvents_Keyin(ByVal keyin As String)
    ' khong dung
End Sub

Private Sub IPrimitiveCommandEvents_Reset()
    KetThuc
End Sub

Private Sub IPrimitiveCommandEvents_Cleanup()
    ' cong cu bi thay -> dam bao co luu/ket thuc
    If Not daKetThuc Then KetThuc
End Sub

Private Sub KetThuc()
    On Error Resume Next
    daKetThuc = True
    Dim ok As Boolean, coLuu As Boolean
    If demChon > 0 And Len(Trim$(csdlPath)) > 0 Then
        Dim dS As New Collection, i As Long, v As clsVung
        For i = 1 To vungs.Count
            Set v = vungs.Item(i)
            If v.daChon Then dS.Add v
        Next i
        ok = LuuCSDL(dS, csdlPath)
        coLuu = True
    End If
    MsgBox "Da tao " & demChon & " thua theo diem bam." & vbCrLf & _
           IIf(coLuu, IIf(ok, "Da luu CSDL: " & csdlPath, "KHONG luu duoc CSDL!"), ""), _
           vbInformation, "Tao vung theo diem"
    CommandState.StartDefaultCommand
    On Error GoTo 0
End Sub

Attribute VB_Name = "clsVung"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' --- Hinh hoc ---
Private mRing() As Double
Public dao As Collection
Public cx As Double
Public cy As Double
Public dt As Double
Public NDao As Long
Public HasRing As Boolean
' --- Thuoc tinh ---
Public soThua As String
Public SoTo As String
Public loaiDat As String
Public TenChu As String
Public tenXa As String
Public DiaChi As String
Public daChon As Boolean        ' danh dau da tao (che do tao vung theo diem)

Private Sub Class_Initialize()
    Set dao = New Collection
    NDao = 0
    dt = 0#
    HasRing = False
    soThua = ""
    SoTo = ""
    loaiDat = ""
    TenChu = ""
    tenXa = ""
    DiaChi = ""
    daChon = False
End Sub
' Ring la mang -> phai boc qua Property (VBA cam mang Public trong class)
Public Property Get ring() As Double()
    ring = mRing
End Property

Public Property Let ring(ByRef v() As Double)
    mRing = v
End Property
Private Sub Class_Terminate()
    Set dao = Nothing
End Sub

Attribute VB_Name = "frmBangDuLieu"
Attribute VB_Base = "0{093F0029-AEB5-4762-A415-1E424A172359}{6CF2BDE9-D612-47FF-9361-0C75255E3CB6}"
Attribute VB_GlobalNameSpace = False
Attribute VB_Creatable = False
Attribute VB_PredeclaredId = True
Attribute VB_Exposed = False
Attribute VB_TemplateDerived = False
Attribute VB_Customizable = False
'============================================================
' frmBangDuLieu - Bang du lieu thua dat (kieu gCadas)
'   Hien 1 bang ngay trong MicroStation thay vi xuat Excel.
'   Nap tu CSDL (.txt) mac dinh theo ten file DGN dang mo.
'   Yeu cau: Class Module "clsNutTL", modCSDL.MoCSDL, modTaoThua.CsdlMacDinh.
'   Tieng Viet ma hoa ChrW() -> dan kieu gi cung khong ra "?".
'============================================================
Option Explicit
' SUA 28/10: lan con chuot cuon ListBox (modCuonChuot)
Private mCuon0 As Object

Private mNut As New Collection
Private mVungs As Collection
Private mLst As clsListEvent
Private mWb As Object            ' workbook Excel vua xuat (de Nap Excel lai)
' SUA 28/10: sap xep theo cot
Private mGoc As Collection
Private mCotSX As Long, mGiamSX As Boolean
Private mTec As Object           ' SUA 22/10: vong do danh dau thua dang chon (phan tu tam)

Private Sub UserForm_Initialize()
    Me.Caption = "Bang du lieu thua dat"      ' thanh tieu de de ASCII
    ' SUA 22/10: thu nho bang (~1/2 dien tich cu)
    Me.Width = 438
    Me.Height = 270

    ' Hang tren: file CSDL + nut
    AddLabel "lblFile", "File CSDL:", 8, 9, 50
    AddText "txtPath", "", 56, 6, 188

    ThemNut "NAP", "N" & ChrW(7841) & "p l" & ChrW(7841) & "i", 248, 5, 54, 20
    ThemNut "EXCEL", "Xu" & ChrW(7845) & "t Excel", 306, 5, 58, 20
    ThemNut "NAPEXCEL", "N" & ChrW(7841) & "p Excel", 368, 5, 58, 20

    ' Hang tieu de cot (label rieng, canh voi ColumnWidths cua ListBox)
    Dim y As Single: y = 32
    AddHead "hStt", "STT", 8, y, 24
    AddHead "hTo", "T" & ChrW(7901), 32, y, 30
    AddHead "hThua", "Th" & ChrW(7917) & "a", 62, y, 36
    AddHead "hLoai", "Lo" & ChrW(7841) & "i " & ChrW(273) & ChrW(7845) & "t", 98, y, 44
    AddHead "hDt", "D.t" & ChrW(237) & "ch (m" & ChrW(178) & ")", 142, y, 56
    AddHead "hChu", "Ch" & ChrW(7911) & " s" & ChrW(7917) & " d" & ChrW(7909) & "ng", 198, y, 120
    AddHead "hDc", ChrW(272) & ChrW(7883) & "a ch" & ChrW(7881), 318, y, 106

    ' Bang du lieu
    Dim lst As Object
    Set lst = Me.Controls.Add("Forms.ListBox.1", "lstData", True)
    Set mCuon0 = DC_GanCuon(lst, Me)     ' SUA 28/10: lan chuot cuon danh sach
    lst.Left = 8: lst.Top = 46: lst.Width = 418: lst.Height = 122
    lst.ColumnCount = 7
    lst.ColumnWidths = "24;30;36;44;56;120;106"
    lst.ListStyle = 0
    lst.Font.Name = "Arial"
    lst.Font.size = 8

    ' o sua truc tiep dong dang chon -> Ghi vao CSDL
    AddLabel "eTo", "T" & ChrW(7901) & ":", 8, 177, 18
    AddText "txtTo", "", 26, 174, 32
    AddLabel "eThua", "Th" & ChrW(7917) & "a:", 62, 177, 26
    AddText "txtThua", "", 88, 174, 42
    AddLabel "eLoai", "Lo" & ChrW(7841) & "i " & ChrW(273) & ChrW(7845) & "t:", 134, 177, 40
    AddText "txtLoai", "", 174, 174, 44
    AddLabel "eChu", "Ch" & ChrW(7911) & ":", 222, 177, 22
    AddText "txtChu", "", 244, 174, 182
    AddLabel "eDc", ChrW(272) & ChrW(7883) & "a ch" & ChrW(7881) & ":", 8, 199, 40
    AddText "txtDc", "", 48, 196, 264
    ThemNut "GHI", "Ghi v" & ChrW(224) & "o CSDL", 316, 195, 110, 20

    ' Dong tong
    AddLabel "lblTong", "", 8, 224, 300

    ThemNut "DONG", ChrW(272) & ChrW(243) & "ng", 356, 220, 70, 22

    Set mLst = New clsListEvent
    Set mLst.lst = lst
    Set mLst.Form = Me

    ' Mac dinh CSDL theo ten file .dgn dang mo
    Me.Controls("txtPath").Text = CsdlMacDinh()
    mCotSX = -1
    NapBang
    GanBamTieuDe        ' SUA 28/10: bam tieu de cot de sap xep
    PhongTo 1.1         ' SUA 28/10: to them 10%
End Sub

Private Sub NapBang()
    Dim lst As Object, path As String
    Set lst = Me.Controls("lstData")
    lst.Clear
    path = Trim$(Me.Controls("txtPath").Text)
    Set mVungs = MoCSDL(path)
    Set mGoc = mVungs: mCotSX = -1: DanhDauCot     ' SUA 28/10
    If mVungs Is Nothing Then Exit Sub
    If mVungs.Count = 0 Then
        Me.Controls("lblTong").Caption = "Ch" & ChrW(432) & "a c" & ChrW(243) & " th" & ChrW(7917) & "a n" & ChrW(224) & "o trong CSDL."
        Exit Sub
    End If

    Dim i As Long, v As clsVung, r As Long, tong As Double
    For i = 1 To mVungs.Count
        Set v = mVungs.Item(i)
        lst.AddItem CStr(i)
        r = lst.ListCount - 1
        lst.List(r, 1) = v.SoTo
        lst.List(r, 2) = v.soThua
        lst.List(r, 3) = v.loaiDat
        lst.List(r, 4) = Format$(Round(v.dt, 1), "0.0")
        lst.List(r, 5) = v.TenChu
        lst.List(r, 6) = v.DiaChi
        tong = tong + v.dt
    Next i

    Me.Controls("lblTong").Caption = "T" & ChrW(7893) & "ng di" & ChrW(7879) & "n t" & ChrW(237) & "ch: " & _
        Format$(tong, "#,##0.0") & " m2   (" & mVungs.Count & " th" & ChrW(7917) & "a)"
End Sub

' Xuat bang hien tai ra Excel (giu lai tuy chon cu)
Private Sub XuatExcel()
    If mVungs Is Nothing Then Exit Sub
    If mVungs.Count = 0 Then Exit Sub
    Dim xl As Object, wb As Object, ws As Object
    On Error Resume Next
    Set xl = CreateObject("Excel.Application")
    On Error GoTo 0
    If xl Is Nothing Then MsgBox "Kh" & ChrW(244) & "ng m" & ChrW(7903) & " " & ChrW(273) & ChrW(432) & ChrW(7907) & "c Excel.", vbExclamation: Exit Sub
    xl.Visible = True
    ' SUA 29/10: viet ca bang 1 lan bang mang + dinh dang chiu loi (loi 1004 tren 1 so may Excel)
    On Error GoTo LoiXL
    Set wb = xl.Workbooks.Add
    Set ws = wb.Worksheets(1)
    Dim i As Long, v As clsVung, n As Long, a() As Variant, c As Variant
    n = mVungs.Count
    On Error Resume Next
    For Each c In Array(2, 3, 4, 6, 7, 8)                ' cot chu: giu nguyen "01", "0012", "=..."
        ws.Columns(c).NumberFormat = "@"
    Next c
    Err.Clear
    On Error GoTo LoiXL
    ReDim a(1 To n + 1, 1 To 8)
    a(1, 1) = "STT"
    a(1, 2) = ChrW(272) & ChrW(7893) & " b" & ChrW(7843) & "n " & ChrW(273) & ChrW(7891)
    a(1, 3) = "Th" & ChrW(7917) & "a"
    a(1, 4) = "Lo" & ChrW(7841) & "i " & ChrW(273) & ChrW(7845) & "t"
    a(1, 5) = "Di" & ChrW(7879) & "n t" & ChrW(237) & "ch (m2)"
    a(1, 6) = "T" & ChrW(234) & "n ch" & ChrW(7911)
    a(1, 7) = ChrW(272) & ChrW(7883) & "a ch" & ChrW(7881)
    a(1, 8) = "Ma (khong sua)"
    For i = 1 To n
        Set v = mVungs.Item(i)
        a(i + 1, 1) = i
        a(i + 1, 2) = CStr(v.SoTo)
        a(i + 1, 3) = CStr(v.soThua)
        a(i + 1, 4) = CStr(v.loaiDat)
        a(i + 1, 5) = Round(v.dt, 1)
        a(i + 1, 6) = CStr(v.TenChu)
        a(i + 1, 7) = CStr(v.DiaChi)
        a(i + 1, 8) = MaThua(v)
    Next i
    ws.Range(ws.Cells(1, 1), ws.Cells(n + 1, 8)).Value = a
    On Error Resume Next
    ws.Range(ws.Cells(1, 1), ws.Cells(1, 8)).Font.Bold = True
    ws.Cells(n + 2, 4).Value = "T" & ChrW(7893) & "ng:"
    ws.Cells(n + 2, 5).Formula = "=SUM(E2:E" & (n + 1) & ")"
    ws.Columns("A:H").AutoFit
    Err.Clear
    On Error GoTo 0
    Set mWb = wb
    MsgBox "S" & ChrW(7917) & "a trong Excel (T" & ChrW(7901) & ", Th" & ChrW(7917) & "a, Lo" & ChrW(7841) & "i " & ChrW(273) & ChrW(7845) & "t, Ch" & ChrW(7911) & ", " & ChrW(272) & ChrW(7883) & "a ch" & ChrW(7881) & "), xong b" & ChrW(7845) & "m 'N" & ChrW(7841) & "p Excel' " & ChrW(273) & ChrW(7875) & " ghi l" & ChrW(7841) & "i CSDL." & vbCrLf & _
           "(C" & ChrW(243) & " th" & ChrW(7875) & " l" & ChrW(432) & "u file Excel r" & ChrW(7891) & "i n" & ChrW(7841) & "p sau)", vbInformation, "Bang du lieu"
    Exit Sub
LoiXL:
    MsgBox "Kh" & ChrW(244) & "ng xu" & ChrW(7845) & "t " & ChrW(273) & ChrW(432) & ChrW(7907) & "c Excel: " & Err.Description & " (" & Err.Number & ")", vbExclamation, "Bang du lieu"
End Sub

Public Sub XuLyNut(ByVal ma As String)
    Select Case ma
        Case "NAP":      NapBang
        Case "EXCEL":    XuatExcel
        Case "NAPEXCEL": NapExcel
        Case "GHI":      GhiDong
        Case "DONG":     TatDanhDau: Unload Me
        Case "SX0", "SX1", "SX2", "SX3", "SX4", "SX5", "SX6": SapXep CLng(Mid$(ma, 3))
    End Select
End Sub

' Bam 1 dong -> dua len o sua
Public Sub DongChon()
    Dim lst As Object, r As Long, v As clsVung
    Set lst = Me.Controls("lstData")
    r = lst.ListIndex
    If r < 0 Or mVungs Is Nothing Then Exit Sub
    If r + 1 > mVungs.Count Then Exit Sub
    Set v = mVungs.Item(r + 1)
    Me.Controls("txtTo").Text = v.SoTo
    Me.Controls("txtThua").Text = v.soThua
    Me.Controls("txtLoai").Text = v.loaiDat
    Me.Controls("txtChu").Text = v.TenChu
    Me.Controls("txtDc").Text = v.DiaChi
    ZoomThua v
    DanhDauThua v       ' SUA 22/10
End Sub

' SUA 22/10: danh dau thua dang chon: vien do dam
'   (phan tu TAM - khong ghi vao ban ve; chon dong khac / dong bang thi mat)
Private Sub DanhDauThua(ByVal v As clsVung)
    Dim rg() As Double, pts() As Point3d, i As Long, n As Long, el As Element
    Dim x1 As Double, y1 As Double, x2 As Double, y2 As Double, r As Double
    TatDanhDau
    On Error Resume Next
    x1 = v.cx: x2 = v.cx: y1 = v.cy: y2 = v.cy
    If v.HasRing Then
        rg = v.ring: n = UBound(rg, 1)
        ReDim pts(0 To n)
        For i = 0 To n
            pts(i).x = rg(i, 0): pts(i).y = rg(i, 1): pts(i).Z = 0#
            If rg(i, 0) < x1 Then x1 = rg(i, 0)
            If rg(i, 0) > x2 Then x2 = rg(i, 0)
            If rg(i, 1) < y1 Then y1 = rg(i, 1)
            If rg(i, 1) > y2 Then y2 = rg(i, 1)
        Next i
        Set el = CreateShapeElement1(Nothing, pts)
        If Not el Is Nothing Then
            el.color = 3: el.LineWeight = 5
            mTec.Add CreateTransientElementContainer1(el, 0, 255, msdDrawingModeNormal)
        End If
    End If
    Err.Clear
End Sub

Private Sub TatDanhDau()
    Dim i As Long
    On Error Resume Next
    If mTec Is Nothing Then Set mTec = New Collection: Exit Sub
    For i = mTec.Count To 1 Step -1
        mTec.Item(i).Reset
        mTec.Remove i
    Next i
End Sub

Private Sub UserForm_Terminate()
    DC_CuonTat
    TatDanhDau
End Sub

' SUA 13/10/2026: bam dong -> zoom view toi thua (thua o giua, rong gap ~3 lan)
Private Sub ZoomThua(ByVal v As clsVung)
    Dim x1 As Double, y1 As Double, x2 As Double, y2 As Double
    Dim rg() As Double, i As Long, d As Double
    On Error Resume Next
    x1 = v.cx: x2 = v.cx: y1 = v.cy: y2 = v.cy
    If v.HasRing Then
        rg = v.ring
        For i = LBound(rg, 1) To UBound(rg, 1)
            If rg(i, 0) < x1 Then x1 = rg(i, 0)
            If rg(i, 0) > x2 Then x2 = rg(i, 0)
            If rg(i, 1) < y1 Then y1 = rg(i, 1)
            If rg(i, 1) > y2 Then y2 = rg(i, 1)
        Next i
    End If
    d = x2 - x1: If y2 - y1 > d Then d = y2 - y1
    If d < 20 Then d = 20
    DC_ZoomVung (x1 + x2) / 2 - d * 1.5, (y1 + y2) / 2 - d * 1.5, _
                (x1 + x2) / 2 + d * 1.5, (y1 + y2) / 2 + d * 1.5
End Sub

' Ghi o sua vao thua dang chon + luu CSDL
Private Sub GhiDong()
    Dim lst As Object, r As Long, v As clsVung
    Set lst = Me.Controls("lstData")
    r = lst.ListIndex
    If r < 0 Or mVungs Is Nothing Then
        DC_ThongBao "B" & ChrW(7845) & "m ch" & ChrW(7885) & "n 1 d" & ChrW(242) & "ng trong b" & ChrW(7843) & "ng tr" & ChrW(432) & ChrW(7899) & "c.", "Bang du lieu", vbExclamation: Exit Sub
    End If
    Set v = mVungs.Item(r + 1)
    v.SoTo = Trim$(Me.Controls("txtTo").Text)
    v.soThua = Trim$(Me.Controls("txtThua").Text)
    v.loaiDat = Trim$(Me.Controls("txtLoai").Text)
    v.TenChu = Trim$(Me.Controls("txtChu").Text)
    v.DiaChi = Trim$(Me.Controls("txtDc").Text)
    If Not LuuCSDL(mVungs, Trim$(Me.Controls("txtPath").Text)) Then
        MsgBox "Kh" & ChrW(244) & "ng ghi " & ChrW(273) & ChrW(432) & ChrW(7907) & "c CSDL: " & Me.Controls("txtPath").Text, vbExclamation, "Bang du lieu": Exit Sub
    End If
    lst.List(r, 1) = v.SoTo: lst.List(r, 2) = v.soThua: lst.List(r, 3) = v.loaiDat
    lst.List(r, 5) = v.TenChu: lst.List(r, 6) = v.DiaChi
    ' sang dong ke tiep cho nhap nhanh
    If r + 1 < lst.ListCount Then lst.ListIndex = r + 1
End Sub

' Nap lai tu Excel (file vua Xuat Excel, da sua) -> ghi CSDL
'   Khop theo cot H (ma toa do tam thua); khong co thi theo STT.
Private Sub NapExcel()
    If mVungs Is Nothing Then Exit Sub
    If mVungs.Count = 0 Then Exit Sub
    Dim ws As Object, xl As Object, wbMo As Object, f As String
    On Error Resume Next
    If Not mWb Is Nothing Then Set ws = mWb.Worksheets(1)
    Err.Clear
    On Error GoTo 0
    If ws Is Nothing Then
        f = DC_ChonFile("Excel (*.xlsx;*.xls)|*.xlsx;*.xls", "Chon file Excel bang du lieu", DC_DocCauHinh("BDL_EXCEL", ""))
        If Len(f) = 0 Then Exit Sub
        DC_GhiCauHinh "BDL_EXCEL", f
        On Error Resume Next
        Set xl = CreateObject("Excel.Application")
        Set wbMo = xl.Workbooks.Open(f, , True)
        On Error GoTo 0
        If wbMo Is Nothing Then MsgBox "Kh" & ChrW(244) & "ng m" & ChrW(7903) & " " & ChrW(273) & ChrW(432) & ChrW(7907) & "c file Excel.", vbExclamation, "Bang du lieu": Exit Sub
        Set ws = wbMo.Worksheets(1)
    End If

    ' tra ma -> chi so thua
    Dim ma As Object, i As Long, v As clsVung
    Set ma = CreateObject("Scripting.Dictionary")
    For i = 1 To mVungs.Count
        Set v = mVungs.Item(i)
        ma(MaThua(v)) = i
    Next i

    Dim r As Long, idx As Long, nDoi As Long, k As String, st As Variant
    r = 2
    Do
        st = ws.Cells(r, 1).Value
        If IsEmpty(st) Or Len(Trim$(CStr(st))) = 0 Then Exit Do
        If Not IsNumeric(st) Then Exit Do              ' dong "Tong:"
        idx = 0
        k = Trim$(CStr(ws.Cells(r, 8).Value))
        If Len(k) > 0 And ma.Exists(k) Then idx = ma(k) Else idx = CLng(st)
        If idx >= 1 And idx <= mVungs.Count Then
            Set v = mVungs.Item(idx)
            If CapNhat(v, ws, r) Then nDoi = nDoi + 1
        End If
        r = r + 1
    Loop
    If Not wbMo Is Nothing Then wbMo.Close False: xl.Quit

    If nDoi = 0 Then MsgBox "Kh" & ChrW(244) & "ng c" & ChrW(243) & " th" & ChrW(7917) & "a n" & ChrW(224) & "o thay " & ChrW(273) & ChrW(7893) & "i.", vbInformation, "Bang du lieu": Exit Sub
    If Not LuuCSDL(mVungs, Trim$(Me.Controls("txtPath").Text)) Then
        MsgBox "Kh" & ChrW(244) & "ng ghi " & ChrW(273) & ChrW(432) & ChrW(7907) & "c CSDL.", vbExclamation, "Bang du lieu": Exit Sub
    End If
    NapBang
    MsgBox ChrW(272) & ChrW(227) & " n" & ChrW(7841) & "p t" & ChrW(7915) & " Excel: " & nDoi & " th" & ChrW(7917) & "a thay " & ChrW(273) & ChrW(7893) & "i, " & ChrW(273) & ChrW(227) & " ghi CSDL." & vbCrLf & _
           "(V" & ChrW(7869) & " l" & ChrW(7841) & "i nh" & ChrW(227) & "n tr" & ChrW(234) & "n b" & ChrW(7843) & "n " & ChrW(273) & ChrW(7891) & ": menu B" & ChrW(7843) & "n " & ChrW(273) & ChrW(7891) & " -> G" & ChrW(225) & "n th" & ChrW(244) & "ng tin / V" & ChrW(7869) & " nh" & ChrW(227) & "n t" & ChrW(7915) & " CSDL)", vbInformation, "Bang du lieu"
End Sub

Private Function CapNhat(ByVal v As clsVung, ByVal ws As Object, ByVal r As Long) As Boolean
    Dim a As String, b As String, c As String, d As String, e As String
    a = OChu(ws.Cells(r, 2).Value): b = OChu(ws.Cells(r, 3).Value): c = OChu(ws.Cells(r, 4).Value)
    d = OChu(ws.Cells(r, 6).Value): e = OChu(ws.Cells(r, 7).Value)
    If a <> v.SoTo Or b <> v.soThua Or c <> v.loaiDat Or d <> v.TenChu Or e <> v.DiaChi Then
        v.SoTo = a: v.soThua = b: v.loaiDat = c: v.TenChu = d: v.DiaChi = e
        CapNhat = True
    End If
End Function

Private Function OChu(ByVal x As Variant) As String
    If IsEmpty(x) Or IsNull(x) Then Exit Function
    OChu = Trim$(CStr(x))
End Function

' Ma nhan dien thua: toa do tam (khong phu thuoc dau phay/cham cua may)
Private Function MaThua(ByVal v As clsVung) As String
    MaThua = Trim$(Str$(Round(v.cx, 2))) & ";" & Trim$(Str$(Round(v.cy, 2)))
End Function

' SUA 28/10: bam tieu de cot -> sap xep (bam lai = dao chieu). So truoc (1-2-3...), chu sau (A-Z).
Private Sub SapXep(ByVal cot As Long)
    Dim n As Long, i As Long, j As Long, gap As Long, tmp As Long, a() As Long, kh() As Variant
    Dim moi As Collection, giam As Boolean, lst As Object, r As Long, v As clsVung
    If mVungs Is Nothing Then Exit Sub
    n = mVungs.Count
    If n < 2 Then Exit Sub
    If mGoc Is Nothing Then Set mGoc = mVungs
    If cot = mCotSX Then giam = Not mGiamSX Else giam = False
    mCotSX = cot: mGiamSX = giam
    ReDim a(1 To n): ReDim kh(1 To n)
    Dim viTri As Object
    Set viTri = CreateObject("Scripting.Dictionary")
    For i = 1 To mGoc.Count
        viTri(ObjPtr(mGoc.Item(i))) = i
    Next i
    For i = 1 To n
        a(i) = i
        Set v = mVungs.Item(i)
        Select Case cot
            Case 0: kh(i) = viTri(ObjPtr(v))
            Case 1: kh(i) = v.SoTo
            Case 2: kh(i) = v.soThua
            Case 3: kh(i) = v.loaiDat
            Case 4: kh(i) = v.dt
            Case 5: kh(i) = v.TenChu
            Case Else: kh(i) = v.DiaChi
        End Select
    Next i
    ' Shell sort tren chi so
    gap = n \ 2
    Do While gap > 0
        For i = gap + 1 To n
            tmp = a(i): j = i
            Do While j > gap
                If SoSanh(kh(a(j - gap)), kh(tmp), giam) <= 0 Then Exit Do
                a(j) = a(j - gap): j = j - gap
            Loop
            a(j) = tmp
        Next i
        gap = gap \ 2
    Loop
    Set moi = New Collection
    For i = 1 To n
        moi.Add mVungs.Item(a(i))
    Next i
    Set mVungs = moi
    ' hien lai bang
    Set lst = Me.Controls("lstData")
    lst.Clear
    For i = 1 To n
        Set v = mVungs.Item(i)
        lst.AddItem CStr(viTri(ObjPtr(v)))
        r = lst.ListCount - 1
        lst.List(r, 1) = v.SoTo
        lst.List(r, 2) = v.soThua
        lst.List(r, 3) = v.loaiDat
        lst.List(r, 4) = Format$(Round(v.dt, 1), "0.0")
        lst.List(r, 5) = v.TenChu
        lst.List(r, 6) = v.DiaChi
    Next i
    DanhDauCot
End Sub

' >0 neu x dung SAU y (tang dan); giam = dao lai. So dung truoc chu.
Private Function SoSanh(ByVal x As Variant, ByVal y As Variant, ByVal giam As Boolean) As Long
    Dim sx As String, sy As String, nX As Boolean, ny As Boolean, k As Long
    sx = Trim$(CStr(x)): sy = Trim$(CStr(y))
    nX = LaSoSX(sx): ny = LaSoSX(sy)
    If Len(sx) = 0 And Len(sy) > 0 Then
        k = 1                                   ' o trong xuong cuoi
    ElseIf Len(sy) = 0 And Len(sx) > 0 Then
        k = -1
    ElseIf nX And ny Then
        If val(Replace(sx, ",", ".")) > val(Replace(sy, ",", ".")) Then
            k = 1
        ElseIf val(Replace(sx, ",", ".")) < val(Replace(sy, ",", ".")) Then
            k = -1
        End If
    ElseIf nX Then
        k = -1
    ElseIf ny Then
        k = 1
    Else
        k = StrComp(sx, sy, vbTextCompare)
    End If
    If giam Then k = -k
    SoSanh = k
End Function

Private Function LaSoSX(ByVal s As String) As Boolean
    If Len(s) = 0 Then Exit Function
    LaSoSX = IsNumeric(Replace(s, ",", "."))
End Function

' Them mui ten len/xuong vao tieu de cot dang sap xep
Private Sub DanhDauCot()
    Dim ten As Variant, i As Long, c As Object, cap As String
    ten = Array("hStt", "hTo", "hThua", "hLoai", "hDt", "hChu", "hDc")
    On Error Resume Next
    For i = 0 To 6
        Set c = Me.Controls(ten(i))
        cap = c.Caption
        If Right$(cap, 2) = " " & ChrW(9650) Or Right$(cap, 2) = " " & ChrW(9660) Then cap = Left$(cap, Len(cap) - 2)
        If i = mCotSX Then cap = cap & IIf(mGiamSX, " " & ChrW(9660), " " & ChrW(9650))
        c.Caption = cap
    Next i
End Sub

' Phong to toan bo form theo he so k (vd 1.1 = to them 10%)
Private Sub PhongTo(ByVal k As Double)
    Dim c As Object, cw As Variant, i As Long, s As String
    On Error Resume Next
    Me.Width = Me.Width * k: Me.Height = Me.Height * k
    For Each c In Me.Controls
        c.Left = c.Left * k: c.Top = c.Top * k
        c.Width = c.Width * k: c.Height = c.Height * k
        c.Font.size = Round(c.Font.size * k)
    Next c
    cw = Split(Me.Controls("lstData").ColumnWidths, ";")
    For i = 0 To UBound(cw)
        If i > 0 Then s = s & ";"
        s = s & CStr(CLng(val(Replace(Replace(cw(i), "pt", ""), ",", ".")) * k))
    Next i
    Me.Controls("lstData").ColumnWidths = Replace(s, ",", ".")
End Sub

' Gan su kien bam cho tieu de cot
Private Sub GanBamTieuDe()
    Dim ten As Variant, i As Long, hd As clsNhanBam, c As Object
    ten = Array("hStt", "hTo", "hThua", "hLoai", "hDt", "hChu", "hDc")
    On Error Resume Next
    For i = 0 To 6
        Set c = Me.Controls(ten(i))
        c.ControlTipText = "B" & ChrW(7845) & "m " & ChrW(273) & ChrW(7875) & " s" & ChrW(7855) & "p x" & ChrW(7871) & "p (b" & ChrW(7845) & "m l" & ChrW(7841) & "i: " & ChrW(273) & ChrW(7843) & "o chi" & ChrW(7873) & "u)"
        c.ForeColor = rgB(0, 0, 160)
        Set hd = New clsNhanBam
        Set hd.lbl = c: Set hd.Form = Me: hd.ma = "SX" & i
        mNut.Add hd
    Next i
End Sub

'--- Tro giup dung control ---
Private Sub AddLabel(ByVal nm As String, ByVal cap As String, _
                     ByVal x As Single, ByVal y As Single, ByVal w As Single)
    Dim c As Object
    Set c = Me.Controls.Add("Forms.Label.1", nm, True)
    c.Caption = cap: c.Left = x: c.Top = y: c.Width = w: c.Height = 16
End Sub

Private Sub AddHead(ByVal nm As String, ByVal cap As String, _
                    ByVal x As Single, ByVal y As Single, ByVal w As Single)
    Dim c As Object
    Set c = Me.Controls.Add("Forms.Label.1", nm, True)
    c.Caption = cap: c.Left = x: c.Top = y: c.Width = w: c.Height = 14
    c.Font.Name = "Arial": c.Font.size = 8: c.Font.Bold = True
End Sub

Private Sub AddText(ByVal nm As String, ByVal txt As String, _
                    ByVal x As Single, ByVal y As Single, ByVal w As Single)
    Dim c As Object
    Set c = Me.Controls.Add("Forms.TextBox.1", nm, True)
    c.Text = txt: c.Left = x: c.Top = y: c.Width = w: c.Height = 18
End Sub

Private Sub ThemNut(ByVal ma As String, ByVal cap As String, _
                    ByVal x As Single, ByVal y As Single, _
                    ByVal w As Single, ByVal h As Single)
    Dim b As Object
    Set b = Me.Controls.Add("Forms.CommandButton.1", "btn" & ma, True)
    b.Caption = cap: b.Left = x: b.Top = y: b.Width = w: b.Height = h
    b.Font.Name = "Arial": b.Font.size = 8
    Dim hd As clsNutTL
    Set hd = New clsNutTL
    Set hd.btn = b: Set hd.Form = Me: hd.ma = ma
    mNut.Add hd
End Sub

Attribute VB_Name = "frmChieuDaiCanh"
Attribute VB_Base = "0{A3B3E977-F395-4971-8F05-09A222745CC1}{92F5BCAC-9B01-4530-864F-8DC89A50BF54}"
Attribute VB_GlobalNameSpace = False
Attribute VB_Creatable = False
Attribute VB_PredeclaredId = True
Attribute VB_Exposed = False
Attribute VB_TemplateDerived = False
Attribute VB_Customizable = False
'============================================================
' frmChieuDaiCanh - "Chieu dai canh" (giong "Ban do canh" LandMap)
'   Can: modChieuDai, clsNutTL, modCauHinh. Tao bang DC_MoFormTuTao.
'============================================================
Option Explicit

Private mNut As New Collection

Private Sub UserForm_Initialize()
    Dim x1 As Single, x2 As Single, c As Object, dS As Collection, i As Long
    Me.Caption = "Chieu dai canh"
    Me.Width = 330: Me.Height = 262
    Me.Font.Name = "Arial": Me.Font.size = 8
    x1 = 8: x2 = 170

    Khung "Th" & ChrW(7875) & " hi" & ChrW(7879) & "n", 4, 4, 316, 132
    Nhan "Font ch" & ChrW(7919), x1 + 4, 20, 80
    Set c = Me.Controls.Add("Forms.ComboBox.1", "cboFont", True)
    c.Left = 92: c.Top = 18: c.Width = 222: c.Height = 18
    Set dS = CDC_DsFont()
    For i = 1 To dS.Count: c.AddItem dS(i): Next i
    c.Text = DC_DocCauHinh("CDC_FONT", "Times New Roman")

    o "K" & ChrW(237) & "ch th" & ChrW(432) & ChrW(7899) & "c ch" & ChrW(7919), "txtCao", DC_DocCauHinh("CDC_CAO", "1.00"), x1, 42
    o "Kho" & ChrW(7843) & "ng c" & ChrW(225) & "ch v" & ChrW(7899) & "i c" & ChrW(7841) & "nh", "txtKc", DC_DocCauHinh("CDC_KC", "0.30"), x1, 64
    o "S" & ChrW(7889) & " ch" & ChrW(7919) & " s" & ChrW(7889) & " th" & ChrW(7853) & "p ph" & ChrW(226) & "n", "txtLe", DC_DocCauHinh("CDC_LE", "2"), x1, 86
    o "Ch" & ChrW(7881) & " ghi c" & ChrW(7841) & "nh l" & ChrW(7899) & "n h" & ChrW(417) & "n(m)", "txtMin", DC_DocCauHinh("CDC_MIN", "0.00"), x1, 108
    O2 "M" & ChrW(224) & "u ch" & ChrW(7919), "txtMau", DC_DocCauHinh("CDC_MAU", "4"), x2, 42, False
    O2 "L" & ChrW(7899) & "p c" & ChrW(7847) & "n hi" & ChrW(7879) & "n", "cboLvVao", DC_DocCauHinh("CDC_LVVAO", "Level 10"), x2, 64, True
    O2 "L" & ChrW(7899) & "p v" & ChrW(7869) & " c" & ChrW(7841) & "nh", "cboLvRa", DC_DocCauHinh("CDC_LVRA", "Level 63"), x2, 86, True

    Khung "T" & ChrW(249) & "y ch" & ChrW(7885) & "n", 4, 142, 316, 44
    chon "chkFence", "S" & ChrW(7917) & " d" & ChrW(7909) & "ng Fence", 12, 160, 90, DC_DocCauHinh("CDC_FENCE", "0") = "1"
    chon "chkPhay", "D" & ChrW(7845) & "u ph" & ChrW(7849) & "y th" & ChrW(7853) & "p ph" & ChrW(226) & "n", 108, 160, 104, DC_DocCauHinh("CDC_PHAY", "1") = "1"
    chon "chkMoc", "T" & ChrW(7841) & "o m" & ChrW(7889) & "c " & ChrW(273) & ChrW(7881) & "nh th" & ChrW(7917) & "a", 214, 160, 102, DC_DocCauHinh("CDC_MOC", "0") = "1"

    Nhan "C" & ChrW(243) & " ch" & ChrW(7885) & "n " & ChrW(273) & ChrW(7889) & "i t" & ChrW(432) & ChrW(7907) & "ng th" & ChrW(236) & " ghi cho " & ChrW(273) & ChrW(7889) & "i t" & ChrW(432) & ChrW(7907) & "ng ch" & ChrW(7885) & "n; kh" & ChrW(244) & "ng ch" & ChrW(7885) & "n: theo Fence / L" & ChrW(7899) & "p c" & ChrW(7847) & "n hi" & ChrW(7879) & "n.", 8, 192, 312
    ThemNut "THUCHIEN", "Th" & ChrW(7921) & "c hi" & ChrW(7879) & "n", 150, 210, 80
    ThemNut "DONG", ChrW(272) & ChrW(243) & "ng", 236, 210, 80
End Sub

Public Sub XuLyNut(ByVal ma As String)
    If ma = "DONG" Then Unload Me: Exit Sub
    Dim n As Long, nMoc As Long, Loi As String
    Luu
    n = CDC_ThucHien(Me.Controls("cboFont").Text, SoCD("txtCao"), CLng(SoCD("txtMau")), SoCD("txtKc"), _
                     CLng(SoCD("txtLe")), Me.Controls("cboLvVao").Text, Me.Controls("cboLvRa").Text, _
                     SoCD("txtMin"), Me.Controls("chkFence").Value, Me.Controls("chkPhay").Value, _
                     Me.Controls("chkMoc").Value, nMoc, Loi)
    If Len(Loi) > 0 Then
        DC_ThongBao Loi, "Chi" & ChrW(7873) & "u d" & ChrW(224) & "i c" & ChrW(7841) & "nh", vbExclamation
    Else
        DC_ThongBao ChrW(272) & ChrW(227) & " ghi " & n & " chi" & ChrW(7873) & "u d" & ChrW(224) & "i c" & ChrW(7841) & "nh" & IIf(nMoc > 0, ", " & nMoc & " m" & ChrW(7889) & "c " & ChrW(273) & ChrW(7881) & "nh", "") & "." & vbCrLf & "(Sai: key-in  undo mark)", "Chi" & ChrW(7873) & "u d" & ChrW(224) & "i c" & ChrW(7841) & "nh"
    End If
End Sub

Private Function SoCD(ByVal nm As String) As Double
    SoCD = val(Replace(Trim$(Me.Controls(nm).Text), ",", "."))
End Function

Private Sub Luu()
    DC_GhiCauHinh "CDC_FONT", Me.Controls("cboFont").Text
    DC_GhiCauHinh "CDC_CAO", Me.Controls("txtCao").Text
    DC_GhiCauHinh "CDC_KC", Me.Controls("txtKc").Text
    DC_GhiCauHinh "CDC_LE", Me.Controls("txtLe").Text
    DC_GhiCauHinh "CDC_MIN", Me.Controls("txtMin").Text
    DC_GhiCauHinh "CDC_MAU", Me.Controls("txtMau").Text
    DC_GhiCauHinh "CDC_LVVAO", Me.Controls("cboLvVao").Text
    DC_GhiCauHinh "CDC_LVRA", Me.Controls("cboLvRa").Text
    DC_GhiCauHinh "CDC_FENCE", IIf(Me.Controls("chkFence").Value, "1", "0")
    DC_GhiCauHinh "CDC_PHAY", IIf(Me.Controls("chkPhay").Value, "1", "0")
    DC_GhiCauHinh "CDC_MOC", IIf(Me.Controls("chkMoc").Value, "1", "0")
End Sub

'------------------------------------------------------------ tao control
' Tieu de nhom (chu dam + gach ngang mo) - khong dung Frame de tranh che control
Private Sub Khung(ByVal cap As String, ByVal x As Single, ByVal y As Single, ByVal w As Single, ByVal h As Single)
    Dim c As Object
    Set c = Me.Controls.Add("Forms.Label.1")
    c.Caption = cap: c.Left = x: c.Top = y: c.Width = w: c.Height = 13
    c.Font.Name = "Arial": c.Font.size = 8: c.Font.Bold = True
    c.BackColor = &HF0E0D0: c.BackStyle = 1
End Sub

Private Sub Nhan(ByVal cap As String, ByVal x As Single, ByVal y As Single, ByVal w As Single)
    Dim c As Object
    Set c = Me.Controls.Add("Forms.Label.1")
    c.Caption = cap: c.Left = x: c.Top = y: c.Width = w: c.Height = 12
    c.Font.Name = "Arial": c.Font.size = 8
    c.ZOrder 0
End Sub

Private Sub o(ByVal cap As String, ByVal nm As String, ByVal gt As String, ByVal x As Single, ByVal y As Single)
    Dim c As Object
    Nhan cap, x + 4, y + 2, 92
    Set c = Me.Controls.Add("Forms.TextBox.1", nm, True)
    c.Left = x + 98: c.Top = y: c.Width = 56: c.Height = 16
    c.Font.Name = "Arial": c.Font.size = 8: c.TextAlign = 3
    c.Text = gt
End Sub

Private Sub O2(ByVal cap As String, ByVal nm As String, ByVal gt As String, ByVal x As Single, ByVal y As Single, ByVal laLevel As Boolean)
    Dim c As Object, dS As Collection, i As Long
    Nhan cap, x, y + 2, 64
    If laLevel Then
        Set c = Me.Controls.Add("Forms.ComboBox.1", nm, True)
        Set dS = CDC_DsLevel()
        For i = 1 To dS.Count: c.AddItem dS(i): Next i
    Else
        Set c = Me.Controls.Add("Forms.TextBox.1", nm, True)
        c.TextAlign = 3
    End If
    c.Left = x + 66: c.Top = y: c.Width = 78: c.Height = 16
    c.Font.Name = "Arial": c.Font.size = 8
    c.Text = gt
End Sub

Private Sub chon(ByVal nm As String, ByVal cap As String, ByVal x As Single, ByVal y As Single, ByVal w As Single, ByVal v As Boolean)
    Dim c As Object
    Set c = Me.Controls.Add("Forms.CheckBox.1", nm, True)
    c.Caption = cap: c.Left = x: c.Top = y: c.Width = w: c.Height = 16
    c.Font.Name = "Arial": c.Font.size = 8
    c.Value = v
End Sub

Private Sub ThemNut(ByVal ma As String, ByVal cap As String, ByVal x As Single, ByVal y As Single, ByVal w As Single)
    Dim b As Object, hd As clsNutTL
    Set b = Me.Controls.Add("Forms.CommandButton.1", "cmd" & ma, True)
    b.Caption = cap: b.Left = x: b.Top = y: b.Width = w: b.Height = 22
    b.Font.Name = "Arial": b.Font.size = 8
    Set hd = New clsNutTL
    Set hd.btn = b: Set hd.Form = Me: hd.ma = ma
    mNut.Add hd
End Sub

Attribute VB_Name = "frmChonKTT"
Attribute VB_Base = "0{F101AF22-C422-4B69-BBEC-B6BF5DBABE8A}{B4BDC786-6844-4F7F-9DD2-5A14D8588DFA}"
Attribute VB_GlobalNameSpace = False
Attribute VB_Creatable = False
Attribute VB_PredeclaredId = True
Attribute VB_Exposed = False
Attribute VB_TemplateDerived = False
Attribute VB_Customizable = False
'============================================================
' frmChonKTT - Chon tinh / kinh tuyen truc truoc khi xem anh ve tinh
'   Can: modKTT, modVeTinh, clsNutTL, modCauHinh.
'============================================================
Option Explicit

Private mNut As New Collection
Private mDs As Collection

Private Sub UserForm_Initialize()
    Dim c As Object, i As Long, chon As String, it As Variant
    Me.Caption = "Chon tinh - kinh tuyen truc"
    Me.Width = 360: Me.Height = 196
    Me.Font.Name = "Arial": Me.Font.size = 8
    Set mDs = KTT_DanhSach()

    Nhan "T" & ChrW(7881) & "nh / th" & ChrW(224) & "nh ph" & ChrW(7889) & " (v" & ChrW(249) & "ng c" & ChrW(7911) & "a b" & ChrW(7843) & "n " & ChrW(273) & ChrW(7891) & " theo " & ChrW(273) & ChrW(7883) & "a gi" & ChrW(7899) & "i C" & ChrW(360) & "):", 8, 8, 340, True
    Set c = Me.Controls.Add("Forms.ComboBox.1", "cboTinh", True)
    c.Left = 8: c.Top = 24: c.Width = 336: c.Height = 18: c.Style = 2
    c.Font.Name = "Arial": c.Font.size = 9
    For i = 1 To mDs.Count
        it = mDs(i): c.AddItem it(0)
    Next i
    chon = DC_DocCauHinh("KTT_TINH", "")
    For i = 0 To c.ListCount - 1
        If c.List(i) = chon Then c.ListIndex = i: Exit For
    Next i

    Nhan "Kinh tuy" & ChrW(7871) & "n tr" & ChrW(7909) & "c (" & ChrW(273) & ChrW(7897) & ", vd 105.5 = 105" & ChrW(176) & "30'):", 8, 52, 200, False
    Set c = Me.Controls.Add("Forms.TextBox.1", "txtKTT", True)
    c.Left = 210: c.Top = 50: c.Width = 70: c.Height = 16: c.Font.Name = "Arial": c.Font.size = 9
    c.Text = DC_DocCauHinh("KTT", "105.5")

    Set c = Me.Controls.Add("Forms.CheckBox.1", "chkD7", True)
    c.Caption = "Chuy" & ChrW(7875) & "n VN-2000 " & ChrW(8594) & " WGS84 b" & ChrW(7857) & "ng 7 tham s" & ChrW(7889) & " (ch" & ChrW(237) & "nh x" & ChrW(225) & "c h" & ChrW(417) & "n)"
    c.Left = 8: c.Top = 74: c.Width = 330: c.Height = 16: c.Font.Name = "Arial": c.Font.size = 8
    c.Value = (DC_DocCauHinh("DATUM7", "1") <> "0")

    Nhan "Sau s" & ChrW(225) & "p nh" & ChrW(7853) & "p 2025 m" & ChrW(7897) & "t t" & ChrW(7881) & "nh m" & ChrW(7899) & "i c" & ChrW(243) & " th" & ChrW(7875) & " g" & ChrW(7891) & "m v" & ChrW(249) & "ng c" & ChrW(361) & " kh" & ChrW(225) & "c kinh tuy" & ChrW(7871) & "n tr" & ChrW(7909) & "c (vd V" & ChrW(297) & "nh Long: V" & ChrW(297) & "nh Long, Tr" & ChrW(224) & " Vinh 105" & ChrW(176) & "30'; B" & ChrW(7871) & "n Tre 105" & ChrW(176) & "45'). Ch" & ChrW(7885) & "n " & ChrW(273) & ChrW(250) & "ng v" & ChrW(249) & "ng c" & ChrW(361) & " c" & ChrW(7911) & "a t" & ChrW(7901) & " b" & ChrW(7843) & "n " & ChrW(273) & ChrW(7891) & ".", 8, 94, 340, False
    Me.Controls(Me.Controls.Count - 1).Height = 28
    Me.Controls(Me.Controls.Count - 1).WordWrap = True
    Me.Controls(Me.Controls.Count - 1).ForeColor = &H808080

    ThemNut "VETINH", "Xem v" & ChrW(7879) & " tinh", 96, 134, 80
    ThemNut "GEARTH", "Google Earth", 180, 134, 80
    ThemNut "DONG", ChrW(272) & ChrW(243) & "ng", 264, 134, 80
End Sub

' Doi tinh -> dien KTT (goi tu XuLyNut khi bam, va khi chay)
Private Function KTTTheoTinh() As Double
    Dim it As Variant, cb As Object
    Set cb = Me.Controls("cboTinh")
    If cb.ListIndex >= 0 Then
        it = mDs(cb.ListIndex + 1)
        KTTTheoTinh = it(1)
    End If
End Function

Public Sub XuLyNut(ByVal ma As String)
    Dim k As Double, kTinh As Double, tay As Double
    If ma = "DONG" Then Unload Me: Exit Sub
    kTinh = KTTTheoTinh()
    tay = val(Replace(Me.Controls("txtKTT").Text, ",", "."))
    ' chon tinh -> dung KTT cua tinh (tru khi nguoi dung sua tay o KTT khac gia tri cu)
    If kTinh > 0 And (tay = val(DC_DocCauHinh("KTT", "105.5")) Or tay <= 0) Then k = kTinh Else k = tay
    If k < 100 Or k > 112 Then
        DC_ThongBao "Kinh tuy" & ChrW(7871) & "n tr" & ChrW(7909) & "c kh" & ChrW(244) & "ng h" & ChrW(7907) & "p l" & ChrW(7879) & " (100 - 112 " & ChrW(273) & ChrW(7897) & ").", "V" & ChrW(7879) & " tinh", vbExclamation
        Exit Sub
    End If
    Me.Controls("txtKTT").Text = CStr(k)
    If Me.Controls("cboTinh").ListIndex >= 0 Then DC_GhiCauHinh "KTT_TINH", Me.Controls("cboTinh").Text
    KTT_ChayViec k, Me.Controls("chkD7").Value, ma
End Sub

Private Sub Nhan(ByVal cap As String, ByVal x As Single, ByVal y As Single, ByVal w As Single, ByVal dam As Boolean)
    Dim c As Object
    Set c = Me.Controls.Add("Forms.Label.1")
    c.Caption = cap: c.Left = x: c.Top = y: c.Width = w: c.Height = 14
    c.Font.Name = "Arial": c.Font.size = 8: c.Font.Bold = dam
End Sub

Private Sub ThemNut(ByVal ma As String, ByVal cap As String, ByVal x As Single, ByVal y As Single, ByVal w As Single)
    Dim b As Object, hd As clsNutTL
    Set b = Me.Controls.Add("Forms.CommandButton.1", "cmd" & ma, True)
    b.Caption = cap: b.Left = x: b.Top = y: b.Width = w: b.Height = 22
    b.Font.Name = "Arial": b.Font.size = 8
    Set hd = New clsNutTL
    Set hd.btn = b: Set hd.Form = Me: hd.ma = ma
    mNut.Add hd
End Sub

Attribute VB_Name = "frmConvertFont"
Attribute VB_Base = "0{6CAFFE17-8877-442A-8D47-8B5D300FD9D4}{DA4A7D07-3FC6-4886-9AEF-BC021DF9DEF9}"
Attribute VB_GlobalNameSpace = False
Attribute VB_Creatable = False
Attribute VB_PredeclaredId = True
Attribute VB_Exposed = False
Attribute VB_TemplateDerived = False
Attribute VB_Customizable = False
'============================================================
' frmConvertFont - Convert font hang loat (giao dien tao dong)
'   Can: modConvertFont, clsNutTL, modCauHinh, modMenuDC (DC_ThongBao)
'============================================================
Option Explicit
' SUA 28/10: lan con chuot cuon ListBox (modCuonChuot)
Private mCuon0 As Object

Private mNut As New Collection
Private mDs As Object           ' LCase(path) -> True (chong trung)
Private mLv() As Long           ' so level theo thu tu trong combo (0 = tat ca)
Private mDangChay As Boolean

Private Sub UserForm_Initialize()
    Me.Caption = "Convert Font"
    Me.Font.Name = "Arial"
    Me.Font.size = 8
    Me.Width = 492
    Me.Height = 300
    Set mDs = CreateObject("Scripting.Dictionary")

    ' --- hang 1: nut them / xoa file
    Dim x As Single: x = 6
    ThemNut "FILE", "+ Th" & ChrW(234) & "m files", "Th" & ChrW(234) & "m c" & ChrW(225) & "c files b" & ChrW(7843) & "n " & ChrW(273) & ChrW(7891), x, 6, 70: x = x + 74
    ThemNut "THUMUC", "+ Th" & ChrW(432) & " m" & ChrW(7909) & "c", "Th" & ChrW(234) & "m th" & ChrW(432) & " m" & ChrW(7909) & "c ch" & ChrW(7913) & "a b" & ChrW(7843) & "n " & ChrW(273) & ChrW(7891), x, 6, 64: x = x + 68
    ThemNut "THUMUCCON", "+ C" & ChrW(7843) & " th" & ChrW(432) & " m" & ChrW(7909) & "c con", "Th" & ChrW(234) & "m b" & ChrW(7843) & "n " & ChrW(273) & ChrW(7891) & " c" & ChrW(7843) & " trong th" & ChrW(432) & " m" & ChrW(7909) & "c con", x, 6, 88: x = x + 92
    ThemNut "HIENTAI", "+ File hi" & ChrW(7879) & "n t" & ChrW(7841) & "i", "Th" & ChrW(234) & "m file b" & ChrW(7843) & "n " & ChrW(273) & ChrW(7891) & " hi" & ChrW(7879) & "n t" & ChrW(7841) & "i", x, 6, 78: x = x + 82
    ThemNut "BOCHON", "B" & ChrW(7887) & " file ch" & ChrW(7885) & "n", "B" & ChrW(7887) & " c" & ChrW(225) & "c file " & ChrW(273) & "ang ch" & ChrW(7885) & "n kh" & ChrW(7887) & "i danh s" & ChrW(225) & "ch", x, 6, 72: x = x + 76
    ThemNut "XOAHET", "X" & ChrW(243) & "a h" & ChrW(7871) & "t", "X" & ChrW(243) & "a to" & ChrW(224) & "n b" & ChrW(7897) & " danh s" & ChrW(225) & "ch files", x, 6, 60

    ' --- hang 2: lop xu ly, kieu chuyen, nut Convert, sao luu
    Dim lb As Object, cL As Object, ck As Object, chk As Object
    Set lb = Me.Controls.Add("Forms.Label.1", "lblLop", True)
    lb.Caption = "L" & ChrW(7899) & "p x" & ChrW(7917) & " l" & ChrW(253): lb.Left = 6: lb.Top = 37: lb.Width = 44: lb.Height = 12
    lb.Font.Name = "Arial": lb.Font.size = 8

    Set cL = Me.Controls.Add("Forms.ComboBox.1", "cboLop", True)
    cL.Left = 50: cL.Top = 34: cL.Width = 122: cL.Height = 18
    cL.Font.Name = "Arial": cL.Font.size = 8: cL.Style = 2
    cL.ControlTipText = "Ch" & ChrW(7881) & " x" & ChrW(7917) & " l" & ChrW(253) & " ch" & ChrW(7919) & " tr" & ChrW(234) & "n l" & ChrW(7899) & "p (level) n" & ChrW(224) & "y"
    NapLevel cL

    Set ck = Me.Controls.Add("Forms.ComboBox.1", "cboKieu", True)
    ck.Left = 178: ck.Top = 34: ck.Width = 142: ck.Height = 18
    ck.Font.Name = "Arial": ck.Font.size = 8: ck.Style = 2
    ck.AddItem "TCVN3 " & ChrW(8594) & " Unicode (Times New Roman)"
    ck.AddItem "Unicode " & ChrW(8594) & " TCVN3 (.VnTime)"
    ck.ListIndex = IIf(val(DC_DocCauHinh("CF_KIEU", "0")) = 1, 1, 0)
    ck.ControlTipText = "Ki" & ChrW(7875) & "u chuy" & ChrW(7875) & "n font"

    ThemNut "CONVERT", "Convert Font", "Chuy" & ChrW(7875) & "n font cho t" & ChrW(7845) & "t c" & ChrW(7843) & " files trong danh s" & ChrW(225) & "ch", 326, 33, 74

    Set chk = Me.Controls.Add("Forms.CheckBox.1", "chkBak", True)
    chk.Caption = "Sao l" & ChrW(432) & "u .bak": chk.Left = 406: chk.Top = 35: chk.Width = 74: chk.Height = 16
    chk.Font.Name = "Arial": chk.Font.size = 8
    chk.Value = (DC_DocCauHinh("CF_BAK", "1") = "1")
    chk.ControlTipText = "Ch" & ChrW(233) & "p file g" & ChrW(7889) & "c th" & ChrW(224) & "nh <t" & ChrW(234) & "n>.dgn.bak tr" & ChrW(432) & ChrW(7899) & "c khi s" & ChrW(7917) & "a"

    ' --- danh sach file
    Dim ls As Object
    Set ls = Me.Controls.Add("Forms.ListBox.1", "lstFile", True)
    Set mCuon0 = DC_GanCuon(ls, Me)     ' SUA 28/10: lan chuot cuon danh sach
    ls.Left = 6: ls.Top = 58: ls.Width = 474: ls.Height = 192
    ls.Font.Name = "Arial": ls.Font.size = 8
    ls.ColumnCount = 2: ls.ColumnWidths = "384;84"
    ls.MultiSelect = 2              ' fmMultiSelectExtended

    ' --- thanh trang thai
    Dim s1 As Object, s2 As Object
    Set s1 = Me.Controls.Add("Forms.Label.1", "lblDem", True)
    s1.Left = 6: s1.Top = 255: s1.Width = 52: s1.Height = 14
    s1.Font.Name = "Arial": s1.Font.size = 8: s1.SpecialEffect = 2
    Set s2 = Me.Controls.Add("Forms.Label.1", "lblPath", True)
    s2.Left = 62: s2.Top = 255: s2.Width = 418: s2.Height = 14
    s2.Font.Name = "Arial": s2.Font.size = 8: s2.SpecialEffect = 2

    ' mo form -> co san file hien tai
    On Error Resume Next
    ThemFile ActiveDesignFile.FullName
    On Error GoTo 0
    CapNhatDem
End Sub

Private Sub NapLevel(ByVal cL As Object)
    Dim lv As Level, n As Long, i As Long, j As Long, t As Long, ts As String
    Dim so() As Long, ten() As String
    cL.Clear
    cL.AddItem "[T" & ChrW(7845) & "t c" & ChrW(7843) & " c" & ChrW(225) & "c l" & ChrW(7899) & "p]"
    ReDim mLv(0 To 0): mLv(0) = -1
    On Error Resume Next
    ReDim so(0 To 0): ReDim ten(0 To 0)
    For Each lv In ActiveDesignFile.Levels
        n = n + 1
        ReDim Preserve so(0 To n): ReDim Preserve ten(0 To n)
        so(n) = lv.Number: ten(n) = lv.Name
    Next lv
    ' sap xep theo so level
    For i = 1 To n - 1
        For j = i + 1 To n
            If so(j) < so(i) Then
                t = so(i): so(i) = so(j): so(j) = t
                ts = ten(i): ten(i) = ten(j): ten(j) = ts
            End If
        Next j
    Next i
    ReDim Preserve mLv(0 To n)
    For i = 1 To n
        cL.AddItem so(i) & " - " & ten(i)
        mLv(i) = so(i)
    Next i
    cL.ListIndex = 0
End Sub

Private Sub ThemNut(ByVal ma As String, ByVal cap As String, ByVal tip As String, _
                    ByVal x As Single, ByVal y As Single, ByVal w As Single)
    Dim b As Object, hd As clsNutTL
    Set b = Me.Controls.Add("Forms.CommandButton.1", "cmd" & ma, True)
    b.Caption = cap: b.Left = x: b.Top = y: b.Width = w: b.Height = 20
    b.Font.Name = "Arial": b.Font.size = 8
    b.ControlTipText = tip
    Set hd = New clsNutTL
    Set hd.btn = b: Set hd.Form = Me: hd.ma = ma
    mNut.Add hd
End Sub

Private Function lst() As Object
    Set lst = Me.Controls("lstFile")
End Function

Private Function ThemFile(ByVal p As String) As Boolean
    Dim k As String
    p = Trim$(p)
    If Len(p) = 0 Then Exit Function
    k = LCase$(p)
    If mDs.Exists(k) Then Exit Function
    mDs.Add k, True
    lst.AddItem p
    lst.List(lst.ListCount - 1, 1) = ""
    ThemFile = True
End Function

Private Sub CapNhatDem()
    Me.Controls("lblDem").Caption = " " & lst.ListCount & " file"
    If lst.ListCount > 0 And lst.ListIndex < 0 Then
        Me.Controls("lblPath").Caption = " " & lst.List(0, 0)
    ElseIf lst.ListCount = 0 Then
        Me.Controls("lblPath").Caption = ""
    End If
End Sub

Private Sub ThemTuDs(ByVal dS As Collection)
    Dim i As Long, n As Long
    For i = 1 To dS.Count
        If ThemFile(CStr(dS.Item(i))) Then n = n + 1
    Next i
    CapNhatDem
    Me.Controls("lblPath").Caption = " " & ChrW(272) & ChrW(227) & " th" & ChrW(234) & "m " & n & " file."
End Sub

Public Sub XuLyNut(ByVal ma As String)
    If mDangChay Then Exit Sub
    Dim dS As Collection, p As String, i As Long
    Select Case ma
    Case "FILE"
        ThemTuDs CF_ChonNhieuFile()
    Case "THUMUC", "THUMUCCON"
        If ma = "THUMUC" Then
            p = CF_ChonThuMuc("Ch" & ChrW(7885) & "n th" & ChrW(432) & " m" & ChrW(7909) & "c ch" & ChrW(7913) & "a b" & ChrW(7843) & "n " & ChrW(273) & ChrW(7891) & " (*.dgn)")
        Else
            p = CF_ChonThuMuc("Ch" & ChrW(7885) & "n th" & ChrW(432) & " m" & ChrW(7909) & "c (l" & ChrW(7845) & "y c" & ChrW(7843) & " th" & ChrW(432) & " m" & ChrW(7909) & "c con)")
        End If
        If Len(p) = 0 Then Exit Sub
        Set dS = New Collection
        Me.Controls("lblPath").Caption = " " & ChrW(272) & "ang t" & ChrW(236) & "m file trong " & p & " ..."
        DoEvents
        CF_GomFileDgn p, (ma = "THUMUCCON"), dS
        ThemTuDs dS
    Case "HIENTAI"
        On Error Resume Next
        p = ActiveDesignFile.FullName
        On Error GoTo 0
        If Len(p) > 0 Then ThemFile p
        CapNhatDem
    Case "BOCHON"
        For i = lst.ListCount - 1 To 0 Step -1
            If lst.Selected(i) Then
                If mDs.Exists(LCase$(lst.List(i, 0))) Then mDs.Remove LCase$(lst.List(i, 0))
                lst.RemoveItem i
            End If
        Next i
        CapNhatDem
    Case "XOAHET"
        lst.Clear
        mDs.RemoveAll
        CapNhatDem
    Case "CONVERT"
        ChayConvert
    End Select
End Sub

Private Sub ChayConvert()
    Dim n As Long, i As Long, cheDo As Long, lvSo As Long, bak As Boolean
    Dim kq As String, soChu As Long, tong As Long, nOK As Long, Loi As String, nLoi As Long
    n = lst.ListCount
    If n = 0 Then
        DC_ThongBao "Danh s" & ChrW(225) & "ch ch" & ChrW(432) & "a c" & ChrW(243) & " file n" & ChrW(224) & "o.", "Convert Font", vbExclamation
        Exit Sub
    End If
    cheDo = Me.Controls("cboKieu").ListIndex
    If cheDo < 0 Then cheDo = 0
    i = Me.Controls("cboLop").ListIndex
    If i < 0 Then i = 0
    lvSo = mLv(i)
    bak = CBool(Me.Controls("chkBak").Value)

    If DC_ThongBao("Chuy" & ChrW(7875) & "n font " & Me.Controls("cboKieu").Text & vbCrLf & _
                   "L" & ChrW(7899) & "p: " & Me.Controls("cboLop").Text & vbCrLf & _
                   "S" & ChrW(7889) & " file: " & n & IIf(bak, " (c" & ChrW(243) & " sao l" & ChrW(432) & "u .bak)", " (KH" & ChrW(212) & "NG sao l" & ChrW(432) & "u)") & vbCrLf & vbCrLf & _
                   "C" & ChrW(225) & "c file s" & ChrW(7869) & " " & ChrW(273) & ChrW(432) & ChrW(7907) & "c ghi " & ChrW(273) & ChrW(232) & ". Ti" & ChrW(7871) & "p t" & ChrW(7909) & "c?", "Convert Font", vbYesNo Or vbQuestion) <> vbYes Then Exit Sub

    DC_GhiCauHinh "CF_KIEU", CStr(cheDo)
    DC_GhiCauHinh "CF_BAK", IIf(bak, "1", "0")

    mDangChay = True
    For i = 0 To n - 1
        lst.List(i, 1) = ""
    Next i
    For i = 0 To n - 1
        Me.Controls("lblDem").Caption = " " & (i + 1) & "/" & n
        Me.Controls("lblPath").Caption = " " & lst.List(i, 0)
        lst.List(i, 1) = ChrW(273) & "ang x" & ChrW(7917) & " l" & ChrW(253) & "..."
        DoEvents
        kq = CF_XuLyFile(CStr(lst.List(i, 0)), cheDo, lvSo, bak, soChu)
        If Len(kq) = 0 Then
            lst.List(i, 1) = soChu & " ch" & ChrW(7919)
            If Len(CF_FileMoi) > 0 Then lst.List(i, 1) = soChu & " ch" & ChrW(7919) & " -> " & Mid$(CF_FileMoi, InStrRev(CF_FileMoi, "\") + 1)
            tong = tong + soChu
            nOK = nOK + 1
        Else
            lst.List(i, 1) = "L" & ChrW(7895) & "i"
            nLoi = nLoi + 1
            If nLoi <= 8 Then Loi = Loi & vbCrLf & "- " & lst.List(i, 0) & ": " & kq
        End If
        DoEvents
    Next i
    mDangChay = False
    On Error Resume Next
    RedrawAllViews
    On Error GoTo 0

    Me.Controls("lblDem").Caption = " " & n & "/" & n
    Me.Controls("lblPath").Caption = " Xong: " & nOK & " file, " & tong & " ch" & ChrW(7919) & "."
    kq = ChrW(272) & ChrW(227) & " x" & ChrW(7917) & " l" & ChrW(253) & " " & nOK & "/" & n & " file, " & ChrW(273) & ChrW(7893) & "i " & tong & " ch" & ChrW(7919) & "."
    If nLoi > 0 Then
        kq = kq & vbCrLf & vbCrLf & "L" & ChrW(7895) & "i " & nLoi & " file:" & Loi
        If nLoi > 8 Then kq = kq & vbCrLf & "..."
    End If
    DC_ThongBao kq, "Convert Font", IIf(nLoi > 0, vbExclamation, vbInformation)
End Sub

Private Sub UserForm_Terminate()
    DC_CuonTat
End Sub

Attribute VB_Name = "frmDiaChinh"
Attribute VB_Base = "0{582DDDD7-EF12-4406-9F91-55F52B028D19}{08CC59D7-86BD-4349-B23C-DF09AFE7EE99}"
Attribute VB_GlobalNameSpace = False
Attribute VB_Creatable = False
Attribute VB_PredeclaredId = True
Attribute VB_Exposed = False
Attribute VB_TemplateDerived = False
Attribute VB_Customizable = False
'============================================================
' MENU CHINH kieu LandMap - frmDiaChinh
'   Hang 1: thanh menu (Label) -> popup menu Windows (modMenuDC)
'   Hang 2: thanh cong cu nhanh (CommandButton)
' Can: clsMenuTop, clsNutTL, modMenuDC
'============================================================
Option Explicit

Private mNut As New Collection     ' clsNutTL  (nut cong cu)
Private mTop As New Collection     ' clsMenuTop (nhan menu)
Private mDangChon As String
Private mDaGanIcon As Boolean

Private Const MAU_HOVER As Long = &HFFE8CC     ' xanh nhat (RGB 204,232,255)
Private Const MAU_VIEN As Long = &HA0A0A0      ' xam
Private Const MAU_CHU_DC As Long = &H8B0000    ' xanh dam (RGB 0,0,139)

Private Sub UserForm_Initialize()
    Me.Caption = "DiaChinhVL V8i - phien ban " & DC_PhienBan()   ' title bar de ASCII
    Me.Font.Name = "Arial"
    Me.Font.size = 9

    '--- Hang 1: thanh menu
    Dim x As Single
    x = 2
    ThemTop "HETHONG", "H" & ChrW(7879) & " th" & ChrW(7889) & "ng", x
    ThemTop "BANDO", "B" & ChrW(7843) & "n " & ChrW(273) & ChrW(7891), x
    ThemTop "BIENTAP", "Bi" & ChrW(234) & "n t" & ChrW(7853) & "p", x
    ThemTop "KIEMKE", "Ki" & ChrW(7875) & "m k" & ChrW(234), x
    ThemTop "TIENICH", "Ti" & ChrW(7879) & "n " & ChrW(237) & "ch", x
    ThemTop "TROGIUP", "Tr" & ChrW(7907) & " gi" & ChrW(250) & "p", x
    Dim wMenu As Single
    wMenu = x

    '--- Duong ke ngang
    Dim ln As Object
    Set ln = Me.Controls.Add("Forms.Label.1", "lnMenu", True)
    ln.Caption = "": ln.BackStyle = 1: ln.BackColor = MAU_VIEN
    ln.Left = 0: ln.Top = 21: ln.Height = 0.75

    '--- Hang 2: thanh cong cu nhanh
    Const y2 As Single = 25
    Const h2 As Single = 20
    Const gx As Single = 2
    x = 4
    ThemNut "TOPO", "Topology", x, y2, 56, h2: x = x + 56 + gx
    ThemNut "TIMLOI", "T" & ChrW(236) & "m l" & ChrW(7895) & "i", x, y2, 50, h2: x = x + 50 + gx
    ThemNut "GANTT", "G" & ChrW(225) & "n TT", x, y2, 50, h2: x = x + 50 + gx
    ThemNut "BANGDL", "B" & ChrW(7843) & "ng DL", x, y2, 54, h2: x = x + 54 + gx
    ThemNut "TRICHLUC", "Tr" & ChrW(237) & "ch l" & ChrW(7909) & "c", x, y2, 56, h2: x = x + 56 + gx
    ThemNut "VETINH", "V" & ChrW(7879) & " tinh", x, y2, 54, h2: x = x + 54 + gx + 6

    Dim vd As Object
    Set vd = Me.Controls.Add("Forms.Label.1", "lnDoc", True)
    vd.Caption = "": vd.BackStyle = 1: vd.BackColor = MAU_VIEN
    vd.Left = x: vd.Top = y2 + 2: vd.Width = 0.75: vd.Height = h2 - 4
    x = x + 8

    Dim tg As Object
    Set tg = Me.Controls.Add("Forms.Label.1", "lblDC", True)
    tg.Caption = ChrW(272) & ChrW(7882) & "A CH" & ChrW(205) & "NH VL"
    tg.Font.Name = "Arial": tg.Font.size = 9: tg.Font.Bold = True
    tg.ForeColor = MAU_CHU_DC: tg.BackStyle = 0
    tg.Left = x: tg.Top = y2 + 4: tg.Width = 90: tg.Height = 14
    x = x + 90

    If wMenu > x Then x = wMenu
    ln.Width = x + 20
    Me.Width = x + 12
    Me.Height = y2 + h2 + 6 + 24
End Sub

'--- them 1 nhan tren thanh menu, tu tinh do rong theo chu
Private Sub ThemTop(ByVal ma As String, ByVal cap As String, ByRef x As Single)
    Dim L As Object
    Set L = Me.Controls.Add("Forms.Label.1", "mnu" & ma, True)
    L.Font.Name = "Arial": L.Font.size = 9
    L.WordWrap = False
    L.Caption = cap
    L.AutoSize = True
    Dim w As Single
    w = L.Width + 14
    L.AutoSize = False
    L.Left = x: L.Top = 3: L.Width = w: L.Height = 16
    L.TextAlign = 2          ' giua
    L.BackStyle = 0
    x = x + w

    Dim t As clsMenuTop
    Set t = New clsMenuTop
    Set t.lbl = L: Set t.Form = Me: t.ma = ma
    mTop.Add t
End Sub

Private Sub ThemNut(ByVal nm As String, ByVal cap As String, _
                    ByVal x As Single, ByVal y As Single, _
                    ByVal w As Single, ByVal h As Single)
    Dim b As Object
    Set b = Me.Controls.Add("Forms.CommandButton.1", "btn" & nm, True)
    b.Caption = cap: b.Left = x: b.Top = y: b.Width = w: b.Height = h
    b.Font.Name = "Arial": b.Font.size = 8
    Dim hd As clsNutTL
    Set hd = New clsNutTL
    Set hd.btn = b: Set hd.Form = Me: hd.ma = nm
    mNut.Add hd
End Sub

'--- to nen nhan menu khi re chuot qua
Public Sub HoverTop(ByVal ma As String)
    If ma = mDangChon Then Exit Sub
    mDangChon = ma
    Dim t As clsMenuTop
    For Each t In mTop
        If t.ma = ma Then
            t.lbl.BackStyle = 1
            t.lbl.BackColor = MAU_HOVER
        Else
            t.lbl.BackStyle = 0
        End If
    Next t
End Sub

'--- gan logo len thanh tieu de (1 lan, khi cua so da hien)
Private Sub UserForm_Activate()
    If Not mDaGanIcon Then
        mDaGanIcon = True
        DC_GanIcon Me.Caption
        BaoBanMoi
    End If
End Sub

' Bao khi co phien ban moi: kiem tra nhanh 1 lan/ngay; co ban moi thi doi
' nhan "DIA CHINH VL" thanh "Co ban moi x.y" (mau do) va hoi cap nhat.
Private Sub BaoBanMoi()
    Dim v As String, vuaBiet As Boolean
    On Error Resume Next
    v = DC_BanMoiNhanh()
    If Len(v) > 0 Then vuaBiet = True Else v = DC_BanMoiDaBiet()
    If Len(v) = 0 Then Exit Sub
    With Me.Controls("lblDC")
        .Caption = "C" & ChrW(243) & " b" & ChrW(7843) & "n m" & ChrW(7899) & "i " & v
        .ForeColor = rgB(200, 0, 0)
    End With
    If vuaBiet Then
        If DC_ThongBao(ChrW(272) & ChrW(227) & " c" & ChrW(243) & " phi" & ChrW(234) & "n b" & ChrW(7843) & "n m" & ChrW(7899) & "i " & v & " (" & ChrW(273) & "ang d" & ChrW(249) & "ng " & DC_PhienBan() & ")." & vbCrLf & vbCrLf & _
                       "C" & ChrW(7853) & "p nh" & ChrW(7853) & "t ngay?", "C" & ChrW(7853) & "p nh" & ChrW(7853) & "t", vbYesNo Or vbQuestion) = vbYes Then
            DC_CapNhatNgay
        End If
    End If
End Sub

Private Sub UserForm_MouseMove(ByVal Button As Integer, ByVal Shift As Integer, ByVal x As Single, ByVal y As Single)
    HoverTop ""
End Sub

'--- goi tu clsMenuTop khi bam nhan menu
Public Sub MoMenuTop(ByVal ma As String, ByVal lbl As Object, ByVal x As Single, ByVal y As Single)
    HoverTop ma
    Dim lenh As String
    lenh = DC_HienMenu(ma, Me.Caption, x, y, lbl.Height)
    HoverTop ""
    If Len(lenh) > 0 Then DC_ChayLenh lenh
End Sub

'--- goi tu clsNutTL khi bam nut cong cu
Public Sub XuLyNut(ByVal ma As String)
    DC_ChayLenh ma
End Sub

Attribute VB_Name = "frmDiemMia"
Attribute VB_Base = "0{8D87299A-08D2-43FE-A351-CF06738A4C4D}{A69395B2-F88A-4540-AE9C-CDA8263D9D44}"
Attribute VB_GlobalNameSpace = False
Attribute VB_Creatable = False
Attribute VB_PredeclaredId = True
Attribute VB_Exposed = False
Attribute VB_TemplateDerived = False
Attribute VB_Customizable = False
'============================================================
' frmDiemMia - Diem mia toa do (kieu LandMap): 3 trang
'   Tep diem mia : dinh dang 5 cot + dau phan cach + chon tep
'   Xem du lieu  : bang Ten / X / Y / H / Ma
'   Hien diem mia: level, co chu, hien ten/H/ma, ky hieu -> Ve diem
'   Can: modDiemMia, modConvertFont (CF_ChonMotFile), clsNutTL, modCauHinh
'============================================================
Option Explicit
' SUA 28/10: lan con chuot cuon ListBox (modCuonChuot)
Private mCuon1 As Object
Private mCuon0 As Object

Private mNut As New Collection
Private mp As Object
Private mCot(0 To 4) As Object
Private mLstF As Object, mLstD As Object

Private Sub UserForm_Initialize()
    Me.Caption = "Diem mia toa do"
    Me.Font.Name = "Arial"
    Me.Font.size = 8
    Me.Width = 404
    Me.Height = 318

    Set mp = Me.Controls.Add("Forms.MultiPage.1", "mpg", True)
    mp.Left = 2: mp.Top = 2: mp.Width = 394: mp.Height = 290
    mp.Font.Name = "Arial": mp.Font.size = 8
    Do While mp.Pages.Count < 3
        mp.Pages.Add
    Loop
    mp.Pages(0).Caption = "T" & ChrW(7879) & "p " & ChrW(273) & "i" & ChrW(7875) & "m mia"
    mp.Pages(1).Caption = "Xem d" & ChrW(7919) & " li" & ChrW(7879) & "u"
    mp.Pages(2).Caption = "Hi" & ChrW(7879) & "n " & ChrW(273) & "i" & ChrW(7875) & "m mia"

    TaoTrang1 mp.Pages(0)
    TaoTrang2 mp.Pages(1)
    TaoTrang3 mp.Pages(2)
    mp.Value = 0
End Sub

'------------------------------------------------------------ trang 1
Private Sub TaoTrang1(ByVal pg As Object)
    Dim i As Long, c As Object, ten As Variant, macDinh() As String, j As Long
    Nhan pg, ChrW(272) & ChrW(7883) & "nh d" & ChrW(7841) & "ng t" & ChrW(7879) & "p t" & ChrW(7885) & "a " & ChrW(273) & ChrW(7897), 6, 4, 200, True
    ten = DM_TenCot()
    macDinh = Split(DC_DocCauHinh("DM_COT", "0,1,2,3,4"), ",")
    For i = 0 To 4
        Nhan pg, "C" & ChrW(7897) & "t " & (i + 1), 6 + i * 76, 20, 70, False
        Set c = pg.Controls.Add("Forms.ComboBox.1", "cboCot" & i, True)
        c.Left = 6 + i * 76: c.Top = 33: c.Width = 72: c.Height = 18
        c.Font.Name = "Arial": c.Font.size = 8: c.Style = 2
        For j = 0 To UBound(ten)
            c.AddItem ten(j)
        Next j
        If i <= UBound(macDinh) Then c.ListIndex = CLng(val(macDinh(i))) Else c.ListIndex = 5
        Set mCot(i) = c
    Next i

    Nhan pg, "D" & ChrW(7845) & "u ph" & ChrW(226) & "n c" & ChrW(225) & "ch c" & ChrW(225) & "c c" & ChrW(7897) & "t", 6, 60, 200, True
    Dim sp As String
    sp = DC_DocCauHinh("DM_SEP", "1,1,1,0")
    HopChon pg, "chkCach", "D" & ChrW(7845) & "u c" & ChrW(225) & "ch (' ')", 6, 76, 70, Mid$(sp, 1, 1) = "1"
    HopChon pg, "chkPhay", "D" & ChrW(7845) & "u ph" & ChrW(7849) & "y (,)", 82, 76, 66, Mid$(sp, 3, 1) = "1"
    HopChon pg, "chkTab", "D" & ChrW(7845) & "u tab", 152, 76, 50, Mid$(sp, 5, 1) = "1"
    HopChon pg, "chkKhac", "K" & ChrW(237) & " t" & ChrW(7921) & " kh" & ChrW(225) & "c", 206, 76, 60, Mid$(sp, 7, 1) = "1"
    Set c = pg.Controls.Add("Forms.TextBox.1", "txtKhac", True)
    c.Left = 268: c.Top = 75: c.Width = 40: c.Height = 16
    c.Font.Name = "Arial": c.Font.size = 8
    c.Text = DC_DocCauHinh("DM_SEPKHAC", ";")

    ThemNut pg, "CHONTEP", "Ch" & ChrW(7885) & "n t" & ChrW(7879) & "p", 300, 98, 82, 20
    ThemNut pg, "BOTEP", "B" & ChrW(7887) & " t" & ChrW(7879) & "p", 214, 98, 82, 20
    Set mLstF = pg.Controls.Add("Forms.ListBox.1", "lstTep", True)
    Set mCuon0 = DC_GanCuon(mLstF, Me)     ' SUA 28/10: lan chuot cuon danh sach
    mLstF.Left = 4: mLstF.Top = 122: mLstF.Width = 380: mLstF.Height = 118
    mLstF.Font.Name = "Arial": mLstF.Font.size = 8
    ThemNut pg, "XEMDL", "Xem d" & ChrW(7919) & " li" & ChrW(7879) & "u >", 300, 244, 82, 20
End Sub

'------------------------------------------------------------ trang 2
Private Sub TaoTrang2(ByVal pg As Object)
    Dim hd As Variant, w As Variant, i As Long, x As Single
    hd = Array("T" & ChrW(234) & "n " & ChrW(273) & "i" & ChrW(7875) & "m", "T" & ChrW(7885) & "a " & ChrW(273) & ChrW(7897) & " X(m)", "T" & ChrW(7885) & "a " & ChrW(273) & ChrW(7897) & " Y(m)", ChrW(272) & ChrW(7897) & " cao H(m)", "M" & ChrW(227) & " " & ChrW(273) & "i" & ChrW(7875) & "m")
    w = Array(70, 80, 80, 66, 70)
    x = 6
    For i = 0 To 4
        Nhan pg, CStr(hd(i)), x, 4, CSng(w(i)), True
        x = x + w(i)
    Next i
    Set mLstD = pg.Controls.Add("Forms.ListBox.1", "lstDL", True)
    Set mCuon1 = DC_GanCuon(mLstD, Me)     ' SUA 28/10: lan chuot cuon danh sach
    mLstD.Left = 4: mLstD.Top = 18: mLstD.Width = 380: mLstD.Height = 222
    mLstD.Font.Name = "Arial": mLstD.Font.size = 8
    mLstD.ColumnCount = 5: mLstD.ColumnWidths = "70;80;80;66;70"
    Nhan pg, "", 6, 248, 280, False, "lblDem"
    ThemNut pg, "SANGVE", "V" & ChrW(7869) & " " & ChrW(273) & "i" & ChrW(7875) & "m >", 300, 244, 82, 20
End Sub

'------------------------------------------------------------ trang 3
Private Sub TaoTrang3(ByVal pg As Object)
    Dim c As Object
    Nhan pg, "Hi" & ChrW(7879) & "n " & ChrW(273) & "i" & ChrW(7875) & "m mia l" & ChrW(234) & "n b" & ChrW(7843) & "n v" & ChrW(7869), 6, 4, 300, True
    Nhan pg, "Level " & ChrW(273) & "i" & ChrW(7875) & "m:", 6, 26, 80, False
    o pg, "txtLv", DC_DocCauHinh("DM_LV", "20"), 100, 24, 50
    Nhan pg, "C" & ChrW(7905) & " ch" & ChrW(7919) & " (m):", 6, 50, 80, False
    o pg, "txtCao", DC_DocCauHinh("DM_CAO", Format$(2 * DC_TyLeBD() / 1000#, "0.0#")), 100, 48, 50
    Nhan pg, "(m" & ChrW(7863) & "c " & ChrW(273) & ChrW(7883) & "nh 2 mm gi" & ChrW(7845) & "y theo t" & ChrW(7927) & " l" & ChrW(7879) & " b" & ChrW(7843) & "n " & ChrW(273) & ChrW(7891) & " 1:" & DC_TyLeBD() & ")", 156, 50, 220, False
    Nhan pg, "S" & ChrW(7889) & " l" & ChrW(7867) & " " & ChrW(273) & ChrW(7897) & " cao:", 6, 74, 80, False
    o pg, "txtLe", DC_DocCauHinh("DM_LE", "2"), 100, 72, 50
    HopChon pg, "chkTen", "Hi" & ChrW(7879) & "n t" & ChrW(234) & "n " & ChrW(273) & "i" & ChrW(7875) & "m", 6, 100, 120, DC_DocCauHinh("DM_TEN", "1") = "1"
    HopChon pg, "chkH", "Hi" & ChrW(7879) & "n " & ChrW(273) & ChrW(7897) & " cao H", 6, 120, 120, DC_DocCauHinh("DM_HH", "1") = "1"
    HopChon pg, "chkMa", "Hi" & ChrW(7879) & "n m" & ChrW(227) & " " & ChrW(273) & "i" & ChrW(7875) & "m", 6, 140, 120, DC_DocCauHinh("DM_MA", "0") = "1"
    Nhan pg, "K" & ChrW(253) & " hi" & ChrW(7879) & "u " & ChrW(273) & "i" & ChrW(7875) & "m:", 150, 100, 80, False
    Set c = pg.Controls.Add("Forms.ComboBox.1", "cboKyHieu", True)
    c.Left = 230: c.Top = 98: c.Width = 100: c.Height = 18
    c.Font.Name = "Arial": c.Font.size = 8: c.Style = 2
    c.AddItem "V" & ChrW(242) & "ng tr" & ChrW(242) & "n"
    c.AddItem "D" & ChrW(7845) & "u c" & ChrW(7897) & "ng (+)"
    c.ListIndex = IIf(DC_DocCauHinh("DM_KH", "0") = "1", 1, 0)
    Nhan pg, "X = t" & ChrW(7885) & "a " & ChrW(273) & ChrW(7897) & " B" & ChrW(7855) & "c, Y = t" & ChrW(7885) & "a " & ChrW(273) & ChrW(7897) & " " & ChrW(272) & ChrW(244) & "ng (VN2000). V" & ChrW(7869) & " xong t" & ChrW(7921) & " zoom t" & ChrW(7899) & "i c" & ChrW(225) & "c " & ChrW(273) & "i" & ChrW(7875) & "m.", 6, 170, 370, False
    ThemNut pg, "VE", "V" & ChrW(7869) & " " & ChrW(273) & "i" & ChrW(7875) & "m", 300, 244, 82, 20
End Sub

'------------------------------------------------------------ xu ly nut
Public Sub XuLyNut(ByVal ma As String)
    Select Case ma
    Case "CHONTEP": ChonTep
    Case "BOTEP"
        If mLstF.ListIndex >= 0 Then mLstF.RemoveItem mLstF.ListIndex
    Case "XEMDL": XemDuLieu
    Case "SANGVE": mp.Value = 2
    Case "VE": VeDiem
    End Select
End Sub

Private Function DauPhanCach() As String
    Dim s As String
    If Me.Controls("chkCach").Value Then s = s & " "
    If Me.Controls("chkPhay").Value Then s = s & ","
    If Me.Controls("chkTab").Value Then s = s & vbTab
    If Me.Controls("chkKhac").Value Then s = s & Trim$(Me.Controls("txtKhac").Text)
    If Len(s) = 0 Then s = " "
    DauPhanCach = s
End Function

Private Sub ChonTep()
    Dim f As String, d As String, a() As String, i As Long
    f = CF_ChonMotFile("T" & ChrW(7885) & "a " & ChrW(273) & ChrW(7897) & " (*.txt;*.csv;*.dat)|*.txt;*.csv;*.dat|T" & ChrW(7845) & "t c" & ChrW(7843) & " (*.*)|*.*", "Ch" & ChrW(7885) & "n t" & ChrW(7879) & "p t" & ChrW(7885) & "a " & ChrW(273) & ChrW(7897) & " " & ChrW(273) & "i" & ChrW(7875) & "m mia")
    If Len(f) = 0 Then Exit Sub
    For i = 0 To mLstF.ListCount - 1
        If StrComp(mLstF.List(i), f, vbTextCompare) = 0 Then Exit Sub
    Next i
    mLstF.AddItem f
    ' tep dau tien: tu doan thu tu cot
    If mLstF.ListCount = 1 Then
        d = DM_DoanCot(f, DauPhanCach())
        If Len(d) > 0 Then
            a = Split(d, ",")
            For i = 0 To 4
                mCot(i).ListIndex = CLng(a(i))
            Next i
        End If
    End If
End Sub

Private Sub XemDuLieu()
    Dim cot(0 To 4) As Long, i As Long, nBo As Long, n As Long, sep As String, r As Long, coX As Boolean, coY As Boolean
    If mLstF.ListCount = 0 Then
        DC_ThongBao "Ch" & ChrW(432) & "a ch" & ChrW(7885) & "n t" & ChrW(7879) & "p t" & ChrW(7885) & "a " & ChrW(273) & ChrW(7897) & ".", ChrW(272) & "i" & ChrW(7875) & "m mia", vbExclamation
        Exit Sub
    End If
    For i = 0 To 4
        cot(i) = mCot(i).ListIndex
        If cot(i) = 1 Then coX = True
        If cot(i) = 2 Then coY = True
    Next i
    If Not (coX And coY) Then
        DC_ThongBao "Ph" & ChrW(7843) & "i c" & ChrW(243) & " m" & ChrW(7897) & "t c" & ChrW(7897) & "t X v" & ChrW(224) & " m" & ChrW(7897) & "t c" & ChrW(7897) & "t Y.", ChrW(272) & "i" & ChrW(7875) & "m mia", vbExclamation
        Exit Sub
    End If
    sep = DauPhanCach()
    DC_GhiCauHinh "DM_COT", cot(0) & "," & cot(1) & "," & cot(2) & "," & cot(3) & "," & cot(4)
    DC_GhiCauHinh "DM_SEP", IIf(Me.Controls("chkCach").Value, "1", "0") & "," & IIf(Me.Controls("chkPhay").Value, "1", "0") & "," & _
                            IIf(Me.Controls("chkTab").Value, "1", "0") & "," & IIf(Me.Controls("chkKhac").Value, "1", "0")
    DC_GhiCauHinh "DM_SEPKHAC", Me.Controls("txtKhac").Text

    DM_XoaDuLieu
    For i = 0 To mLstF.ListCount - 1
        n = n + DM_DocFile(CStr(mLstF.List(i)), cot, sep, nBo)
    Next i
    mLstD.Clear
    For i = 1 To DM_N
        mLstD.AddItem DM_Ten(i)
        r = mLstD.ListCount - 1
        mLstD.List(r, 1) = Format$(DM_X(i), "0.000")
        mLstD.List(r, 2) = Format$(DM_Y(i), "0.000")
        mLstD.List(r, 3) = DM_H(i)
        mLstD.List(r, 4) = DM_Ma(i)
    Next i
    Me.Controls("lblDem").Caption = DM_N & " " & ChrW(273) & "i" & ChrW(7875) & "m" & IIf(nBo > 0, " (b" & ChrW(7887) & " qua " & nBo & " d" & ChrW(242) & "ng kh" & ChrW(244) & "ng ph" & ChrW(7843) & "i t" & ChrW(7885) & "a " & ChrW(273) & ChrW(7897) & ")", "")
    mp.Value = 1
    If DM_N = 0 Then DC_ThongBao "Kh" & ChrW(244) & "ng " & ChrW(273) & ChrW(7885) & "c " & ChrW(273) & ChrW(432) & ChrW(7907) & "c " & ChrW(273) & "i" & ChrW(7875) & "m n" & ChrW(224) & "o. Ki" & ChrW(7875) & "m tra l" & ChrW(7841) & "i " & ChrW(273) & ChrW(7883) & "nh d" & ChrW(7841) & "ng c" & ChrW(7897) & "t v" & ChrW(224) & " d" & ChrW(7845) & "u ph" & ChrW(226) & "n c" & ChrW(225) & "ch.", ChrW(272) & "i" & ChrW(7875) & "m mia", vbExclamation
End Sub

Private Sub VeDiem()
    Dim lv As Long, cao As Double, le As Long, n As Long, kh As Long
    If DM_N = 0 Then
        DC_ThongBao "Ch" & ChrW(432) & "a c" & ChrW(243) & " d" & ChrW(7919) & " li" & ChrW(7879) & "u. Ch" & ChrW(7885) & "n t" & ChrW(7879) & "p r" & ChrW(7891) & "i b" & ChrW(7845) & "m 'Xem d" & ChrW(7919) & " li" & ChrW(7879) & "u' tr" & ChrW(432) & ChrW(7899) & "c.", ChrW(272) & "i" & ChrW(7875) & "m mia", vbExclamation
        mp.Value = 0
        Exit Sub
    End If
    lv = CLng(val(Me.Controls("txtLv").Text)): If lv <= 0 Then lv = 20
    cao = val(Replace(Me.Controls("txtCao").Text, ",", ".")): If cao <= 0 Then cao = 1
    le = CLng(val(Me.Controls("txtLe").Text)): If le < 0 Then le = 0
    kh = Me.Controls("cboKyHieu").ListIndex: If kh < 0 Then kh = 0
    DC_GhiCauHinh "DM_LV", CStr(lv)
    DC_GhiCauHinh "DM_CAO", Me.Controls("txtCao").Text
    DC_GhiCauHinh "DM_LE", CStr(le)
    DC_GhiCauHinh "DM_TEN", IIf(Me.Controls("chkTen").Value, "1", "0")
    DC_GhiCauHinh "DM_HH", IIf(Me.Controls("chkH").Value, "1", "0")
    DC_GhiCauHinh "DM_MA", IIf(Me.Controls("chkMa").Value, "1", "0")
    DC_GhiCauHinh "DM_KH", CStr(kh)
    n = DM_Ve(lv, cao, CBool(Me.Controls("chkTen").Value), CBool(Me.Controls("chkH").Value), _
              CBool(Me.Controls("chkMa").Value), kh, le)
    DC_ThongBao ChrW(272) & ChrW(227) & " v" & ChrW(7869) & " " & n & " " & ChrW(273) & "i" & ChrW(7875) & "m l" & ChrW(234) & "n level " & lv & ".", ChrW(272) & "i" & ChrW(7875) & "m mia"
End Sub

'------------------------------------------------------------ tao control
Private Sub Nhan(ByVal pg As Object, ByVal cap As String, ByVal x As Single, ByVal y As Single, _
                 ByVal w As Single, ByVal dam As Boolean, Optional ByVal nm As String = "")
    Dim c As Object
    If Len(nm) = 0 Then Set c = pg.Controls.Add("Forms.Label.1") Else Set c = pg.Controls.Add("Forms.Label.1", nm, True)
    c.Caption = cap: c.Left = x: c.Top = y: c.Width = w: c.Height = 13
    c.Font.Name = "Arial": c.Font.size = 8: c.Font.Bold = dam
End Sub

Private Sub o(ByVal pg As Object, ByVal nm As String, ByVal gt As String, ByVal x As Single, ByVal y As Single, ByVal w As Single)
    Dim c As Object
    Set c = pg.Controls.Add("Forms.TextBox.1", nm, True)
    c.Left = x: c.Top = y: c.Width = w: c.Height = 16
    c.Font.Name = "Arial": c.Font.size = 8
    c.Text = gt
End Sub

Private Sub HopChon(ByVal pg As Object, ByVal nm As String, ByVal cap As String, ByVal x As Single, ByVal y As Single, _
                    ByVal w As Single, ByVal chon As Boolean)
    Dim c As Object
    Set c = pg.Controls.Add("Forms.CheckBox.1", nm, True)
    c.Caption = cap: c.Left = x: c.Top = y: c.Width = w: c.Height = 16
    c.Font.Name = "Arial": c.Font.size = 8
    c.Value = chon
End Sub

Private Sub ThemNut(ByVal pg As Object, ByVal ma As String, ByVal cap As String, ByVal x As Single, ByVal y As Single, _
                    ByVal w As Single, ByVal h As Single)
    Dim b As Object, hd As clsNutTL
    Set b = pg.Controls.Add("Forms.CommandButton.1", "cmd" & ma, True)
    b.Caption = cap: b.Left = x: b.Top = y: b.Width = w: b.Height = h
    b.Font.Name = "Arial": b.Font.size = 8
    Set hd = New clsNutTL
    Set hd.btn = b: Set hd.Form = Me: hd.ma = ma
    mNut.Add hd
End Sub

Private Sub UserForm_Terminate()
    DC_CuonTat
End Sub

Attribute VB_Name = "frmDonViHC"
Attribute VB_Base = "0{20CD9CA7-DFEA-424E-83D3-C39A076D4D87}{F1171D9A-1630-4AD0-B224-16E6868545E9}"
Attribute VB_GlobalNameSpace = False
Attribute VB_Creatable = False
Attribute VB_PredeclaredId = True
Attribute VB_Exposed = False
Attribute VB_TemplateDerived = False
Attribute VB_Customizable = False
'============================================================
' frmDonViHC - Thiet lap don vi hanh chinh (menu He thong)
'   Luu vao C:\DiaChinhVL\DiaChinhVL.ini -> Trich luc tu dien san.
'   Can clsNutTL, clsComboEvent, modMaXa, modCauHinh.
'============================================================
Option Explicit

Private Const MAXA_PATH As String = "C:\DiaChinhVL\MaXaVN.txt"

Private mNut As New Collection
Private mCbo As clsComboEvent

Private Sub UserForm_Initialize()
    Me.Caption = "Thiet lap don vi hanh chinh"
    Me.Font.Name = "Arial"
    Me.Font.size = 8
    Me.Width = 340
    Me.Height = 222

    Const x As Single = 10
    Dim tg As Object
    Set tg = Me.Controls.Add("Forms.Label.1", "lblTieuDe", True)
    tg.Caption = ChrW(272) & ChrW(416) & "N V" & ChrW(7882) & " H" & ChrW(192) & "NH CH" & ChrW(205) & "NH (d" & ChrW(249) & "ng khi xu" & ChrW(7845) & "t tr" & ChrW(237) & "ch l" & ChrW(7909) & "c)"
    tg.Left = x: tg.Top = 8: tg.Width = 310: tg.Height = 14
    tg.Font.Name = "Arial": tg.Font.size = 8: tg.Font.Bold = True

    AddLbl "lblTinh", "T" & ChrW(7881) & "nh / th" & ChrW(224) & "nh ph" & ChrW(7889) & ":", x, 34
    Dim cboT As Object
    Set cboT = Me.Controls.Add("Forms.ComboBox.1", "cboTinh", True)
    cboT.Left = x + 104: cboT.Top = 32: cboT.Width = 200: cboT.Height = 18
    cboT.Font.Name = "Arial": cboT.Font.size = 8

    AddLbl "lblXa", "X" & ChrW(227) & " / ph" & ChrW(432) & ChrW(7901) & "ng:", x, 60
    Dim cboX As Object
    Set cboX = Me.Controls.Add("Forms.ComboBox.1", "cboXa", True)
    cboX.Left = x + 104: cboX.Top = 58: cboX.Width = 200: cboX.Height = 18
    cboX.Font.Name = "Arial": cboX.Font.size = 8

    AddLbl "lblHuyen", "Huy" & ChrW(7879) & "n (n" & ChrW(7871) & "u c" & ChrW(243) & "):", x, 86
    Dim TH As Object
    Set TH = Me.Controls.Add("Forms.TextBox.1", "txtHuyen", True)
    TH.Left = x + 104: TH.Top = 84: TH.Width = 200: TH.Height = 16
    TH.Font.Name = "Arial": TH.Font.size = 8

    AddLbl "lblKTT", "Kinh tuy" & ChrW(7871) & "n tr" & ChrW(7909) & "c:", x, 110
    Dim ck As Object
    Set ck = Me.Controls.Add("Forms.ComboBox.1", "cboKTT", True)
    ck.Left = x + 104: ck.Top = 108: ck.Width = 200: ck.Height = 18
    ck.Font.Name = "Arial": ck.Font.size = 8
    ck.AddItem "105.5  (105" & ChrW(176) & "30' - V" & ChrW(297) & "nh Long, Tr" & ChrW(224) & " Vinh c" & ChrW(361) & ")"
    ck.AddItem "105.75 (105" & ChrW(176) & "45' - B" & ChrW(7871) & "n Tre c" & ChrW(361) & ")"
    ck.AddItem "105.0  (105" & ChrW(176) & "00')"
    ck.AddItem "104.75 (104" & ChrW(176) & "45')"
    ck.AddItem "106.0  (106" & ChrW(176) & "00')"
    ck.AddItem "106.25 (106" & ChrW(176) & "15')"

    Dim gc As Object
    Set gc = Me.Controls.Add("Forms.Label.1", "lblGhiChu", True)
    gc.Caption = "Tr" & ChrW(237) & "ch l" & ChrW(7909) & "c t" & ChrW(7921) & " " & ChrW(273) & "i" & ChrW(7873) & "n s" & ChrW(7861) & "n; kinh tuy" & ChrW(7871) & "n tr" & ChrW(7909) & "c d" & ChrW(249) & "ng khi xem " & ChrW(7843) & "nh v" & ChrW(7879) & " tinh."
    gc.Left = x: gc.Top = 134: gc.Width = 310: gc.Height = 14
    gc.Font.Name = "Arial": gc.Font.size = 8: gc.Font.Italic = True

    ThemNut "LUU", "L" & ChrW(432) & "u", 150, 154
    ThemNut "DONG", ChrW(272) & ChrW(243) & "ng", 238, 154

    ' Nap danh sach Tinh/Xa
    Dim tinh As String, xa As String, dS As Collection, i As Long
    If NapMaXa(MAXA_PATH) Then
        Set dS = DsTinh()
        For i = 1 To dS.Count
            cboT.AddItem dS.Item(i)
        Next i
    End If
    tinh = DC_DocCauHinh("TINH", "T" & ChrW(7881) & "nh V" & ChrW(297) & "nh Long")
    cboT.Value = tinh
    FillXa tinh
    xa = DC_DocCauHinh("XA", "")
    If Len(xa) > 0 Then cboX.Value = xa
    TH.Text = DC_DocCauHinh("HUYEN", "")
    Dim k As String, i2 As Long
    k = DC_DocCauHinh("KTT", "105.5")
    ck.Value = k
    For i2 = 0 To ck.ListCount - 1
        If val(ck.List(i2)) = val(k) Then ck.ListIndex = i2: Exit For
    Next i2

    Set mCbo = New clsComboEvent
    Set mCbo.cbo = cboT
    Set mCbo.Form = Me
End Sub

' Goi tu clsComboEvent khi doi Tinh
Public Sub TinhDoi()
    FillXa CStr(Me.Controls("cboTinh").Value)
End Sub

Private Sub FillXa(ByVal tinh As String)
    Dim cboX As Object, dS As Collection, i As Long
    Set cboX = Me.Controls("cboXa")
    cboX.Clear
    If Not DaNapMaXa() Then Exit Sub
    Set dS = DsXa(tinh)
    For i = 1 To dS.Count
        cboX.AddItem dS.Item(i)
    Next i
    If dS.Count > 0 Then cboX.ListIndex = 0
End Sub

Private Sub AddLbl(ByVal nm As String, ByVal cap As String, ByVal x As Single, ByVal y As Single)
    Dim c As Object
    Set c = Me.Controls.Add("Forms.Label.1", nm, True)
    c.Caption = cap: c.Left = x: c.Top = y: c.Width = 100: c.Height = 14
    c.Font.Name = "Arial": c.Font.size = 8
End Sub

Private Sub ThemNut(ByVal ma As String, ByVal cap As String, ByVal x As Single, ByVal y As Single)
    Dim b As Object, hd As clsNutTL
    Set b = Me.Controls.Add("Forms.CommandButton.1", "cmd" & ma, True)
    b.Caption = cap: b.Left = x: b.Top = y: b.Width = 80: b.Height = 24
    b.Font.Name = "Arial": b.Font.size = 8
    Set hd = New clsNutTL
    Set hd.btn = b: Set hd.Form = Me: hd.ma = ma
    mNut.Add hd
End Sub

Public Sub XuLyNut(ByVal ma As String)
    If ma = "DONG" Then Unload Me: Exit Sub
    If ma = "LUU" Then
        If Len(Trim$(CStr(Me.Controls("cboXa").Value))) = 0 Then
            DC_ThongBao "Ch" & ChrW(432) & "a ch" & ChrW(7885) & "n x" & ChrW(227) & " / ph" & ChrW(432) & ChrW(7901) & "ng.", ChrW(272) & ChrW(417) & "n v" & ChrW(7883) & " h" & ChrW(224) & "nh ch" & ChrW(237) & "nh", vbExclamation
            Exit Sub
        End If
        DC_GhiCauHinh "TINH", Trim$(CStr(Me.Controls("cboTinh").Value))
        DC_GhiCauHinh "XA", Trim$(CStr(Me.Controls("cboXa").Value))
        DC_GhiCauHinh "HUYEN", Trim$(Me.Controls("txtHuyen").Text)
        If val(CStr(Me.Controls("cboKTT").Value)) >= 100 Then
            DC_GhiCauHinh "KTT", CStr(val(CStr(Me.Controls("cboKTT").Value)))
        End If
        DC_ThongBao ChrW(272) & ChrW(227) & " l" & ChrW(432) & "u " & ChrW(273) & ChrW(417) & "n v" & ChrW(7883) & " h" & ChrW(224) & "nh ch" & ChrW(237) & "nh:" & vbCrLf & _
                    Me.Controls("cboXa").Value & " - " & Me.Controls("cboTinh").Value, _
                    ChrW(272) & ChrW(417) & "n v" & ChrW(7883) & " h" & ChrW(224) & "nh ch" & ChrW(237) & "nh"
        Unload Me
    End If
End Sub

Attribute VB_Name = "frmGanNhan"
Attribute VB_Base = "0{22D47986-77D4-43CF-9617-1063773F06C5}{5AE7D6D2-1FDB-40C3-A876-2914FDDB0143}"
Attribute VB_GlobalNameSpace = False
Attribute VB_Creatable = False
Attribute VB_PredeclaredId = True
Attribute VB_Exposed = False
Attribute VB_TemplateDerived = False
Attribute VB_Customizable = False
Option Explicit
' SUA 28/10: lan con chuot cuon ListBox (modCuonChuot)
Private mCuon0 As Object
 
Private mNut As New Collection
 
Private Sub UserForm_Initialize()
    Me.Caption = "Gan thong tin tu nhan / CSDL"
    Me.Width = 400
    Me.Height = 420
 
    AddLabel "lblLv", "Lop ranh (tick chon):", 8, 6, 160
    Dim lst As Object
    Set lst = Me.Controls.Add("Forms.ListBox.1", "lstLevel", True)
    Set mCuon0 = DC_GanCuon(lst, Me)     ' SUA 28/10: lan chuot cuon danh sach
    lst.Left = 8: lst.Top = 22: lst.Width = 150: lst.Height = 340
    lst.ListStyle = 1: lst.MultiSelect = 1
    Dim i As Long
    For i = 1 To 63
        lst.AddItem "Level " & i
    Next i
 
    Dim x As Single: x = 175
    AddLabel "lblH", "Level chua tung thong tin:", x, 6, 210
    AddPair "To ban do:", "txtLvTo", "", x, 24
    AddPair "So hieu thua:", "txtLvSo", "", x, 50
    AddPair "Loai dat:", "txtLvLoai", "", x, 76
    AddPair "Ten chu:", "txtLvChu", "", x, 102
    AddPair "Dia chi:", "txtLvDiaChi", "", x, 128
 
    AddPair "Snap:", "txtSnap", "0.05", x, 160
    AddPair "Lop nhan:", "txtLvNhan", "Level 6", x, 186
    AddPair "Co chu nhan:", "txtCao", "1", x, 212
 
    Dim c As Object
    Set c = Me.Controls.Add("Forms.CheckBox.1", "chkCSDL", True)
    c.Caption = "Xuat CSDL (CSV)": c.Left = x: c.Top = 244: c.Width = 200: c.Height = 16
    c.Value = True
    AddPair "Duong dan CSDL:", "txtPath", "C:\DiaChinhVL\csdl.csv", x, 264
 
    Dim b1 As Object, b2 As Object
    Set b1 = Me.Controls.Add("Forms.CommandButton.1", "cmdOK", True)
    b1.Caption = "Chap nhan": b1.Left = 195: b1.Top = 356: b1.Width = 95: b1.Height = 26
    Set b2 = Me.Controls.Add("Forms.CommandButton.1", "cmdDong", True)
    b2.Caption = "Dong": b2.Left = 298: b2.Top = 356: b2.Width = 80: b2.Height = 26
    Dim h1 As clsNutTL, h2 As clsNutTL
    Set h1 = New clsNutTL: Set h1.btn = b1: Set h1.Form = Me: h1.ma = "OK": mNut.Add h1
    Set h2 = New clsNutTL: Set h2.btn = b2: Set h2.Form = Me: h2.ma = "DONG": mNut.Add h2
End Sub
 
Private Sub AddLabel(ByVal nm As String, ByVal cap As String, _
                     ByVal x As Single, ByVal y As Single, ByVal w As Single)
    Dim c As Object
    Set c = Me.Controls.Add("Forms.Label.1", nm, True)
    c.Caption = cap: c.Left = x: c.Top = y: c.Width = w: c.Height = 14
End Sub
 
' Nhan + o nhap tren cung 1 hang
Private Sub AddPair(ByVal cap As String, ByVal nm As String, ByVal txt As String, _
                    ByVal x As Single, ByVal y As Single)
    AddLabel "lbl_" & nm, cap, x, y + 2, 95
    Dim c As Object
    Set c = Me.Controls.Add("Forms.TextBox.1", nm, True)
    c.Text = txt: c.Left = x + 100: c.Top = y: c.Width = 110: c.Height = 16
End Sub
 
Public Sub XuLyNut(ByVal ma As String)
    If ma = "DONG" Then Unload Me: Exit Sub
 
    Dim lst As Object, csv As String, i As Long
    Set lst = Me.Controls("lstLevel")
    For i = 0 To lst.ListCount - 1
        If lst.Selected(i) Then
            If Len(csv) > 0 Then csv = csv & ","
            csv = csv & lst.List(i)
        End If
    Next i
    If Len(csv) = 0 Then MsgBox "Chua chon level ranh.", vbExclamation: Exit Sub
 
    Me.Hide
    ChayGanNhan csv, _
                Me.Controls("txtLvTo").Text, Me.Controls("txtLvSo").Text, _
                Me.Controls("txtLvLoai").Text, Me.Controls("txtLvChu").Text, _
                Me.Controls("txtLvDiaChi").Text, val(Me.Controls("txtSnap").Text), _
                Me.Controls("txtLvNhan").Text, val(Me.Controls("txtCao").Text), _
                Me.Controls("chkCSDL").Value, Me.Controls("txtPath").Text
    Me.Show vbModeless
End Sub

Private Sub UserForm_Terminate()
    DC_CuonTat
End Sub

Attribute VB_Name = "frmGanTT"
Attribute VB_Base = "0{C045EA6E-65E2-440D-AF02-CB7012D18D9D}{816EEF0D-DED0-48F1-8981-027BB3E5A7C3}"
Attribute VB_GlobalNameSpace = False
Attribute VB_Creatable = False
Attribute VB_PredeclaredId = True
Attribute VB_Exposed = False
Attribute VB_TemplateDerived = False
Attribute VB_Customizable = False
'============================================================
' frmGanTT - Gan thong tin tu nhan (tu CSDL) - Viet hoa ChrW, Arial
' Can Class Module "clsNutTL". Tieu de thanh de ASCII (font he thong).
'============================================================
Option Explicit

Private mNut As New Collection

Private Sub UserForm_Initialize()
    Me.Caption = "Gan thong tin tu nhan (tu CSDL)"
    Me.Font.Name = "Arial"
    Me.Font.size = 8
    Me.Width = 380
    Me.Height = 372

    Dim x As Single: x = 12
    AddLabel "lblPath", ChrW(272) & ChrW(432) & ChrW(7901) & "ng d" & ChrW(7851) & "n file CSDL:", x, 8, 200
    AddText "txtPath", "", x, 24, 340

    AddLabel "lblH", "Level ch" & ChrW(7913) & "a t" & ChrW(7915) & "ng th" & ChrW(244) & "ng tin:", x, 52, 250
    AddPair "S" & ChrW(7889) & " hi" & ChrW(7879) & "u th" & ChrW(7917) & "a:", "txtLvSo", "", x, 72
    AddPair "T" & ChrW(7901) & " b" & ChrW(7843) & "n " & ChrW(273) & ChrW(7891) & ":", "txtLvTo", "", x, 96
    AddPair "Lo" & ChrW(7841) & "i " & ChrW(273) & ChrW(7845) & "t:", "txtLvLoai", "", x, 120
    AddPair "T" & ChrW(234) & "n ch" & ChrW(7911) & ":", "txtLvChu", "", x, 144
    AddPair ChrW(272) & ChrW(7883) & "a ch" & ChrW(7881) & ":", "txtLvDC", "", x, 168

    Dim c As Object
    Set c = Me.Controls.Add("Forms.CheckBox.1", "chkVe", True)
    c.Caption = "V" & ChrW(7869) & " nh" & ChrW(227) & "n l" & ChrW(234) & "n b" & ChrW(7843) & "n " & ChrW(273) & ChrW(7891) & " sau khi g" & ChrW(225) & "n"
    c.Left = x: c.Top = 196: c.Width = 300: c.Height = 16: c.Value = False   ' mac dinh KHONG ve nhan
    ' SUA 25/10: ghi chu mo duoi o ve nhan
    Dim gc As Object
    Set gc = Me.Controls.Add("Forms.Label.1", "lblGhiChuNhan", True)
    gc.Caption = "V" & ChrW(7869) & " nh" & ChrW(227) & "n th" & ChrW(7917) & "a theo Th" & ChrW(244) & "ng t" & ChrW(432) & " 26: lo" & ChrW(7841) & "i " & ChrW(273) & ChrW(7845) & "t, s" & ChrW(7889) & " th" & ChrW(7917) & "a / di" & ChrW(7879) & "n t" & ChrW(237) & "ch th" & ChrW(224) & "nh 1 kh" & ChrW(7889) & "i (m" & ChrW(7863) & "c " & ChrW(273) & ChrW(7883) & "nh l" & ChrW(7899) & "p 13)"
    gc.Left = x + 16: gc.Top = 213: gc.Width = 340: gc.Height = 12
    gc.Font.Name = "Arial": gc.Font.size = 7: gc.ForeColor = rgB(128, 128, 128)
    c.Font.Name = "Arial": c.Font.size = 8
    Dim c2 As Object
    Set c2 = Me.Controls.Add("Forms.CheckBox.1", "chkXoaCu", True)
    c2.Caption = "X" & ChrW(243) & "a gi" & ChrW(225) & " tr" & ChrW(7883) & " c" & ChrW(361) & " c" & ChrW(7911) & "a c" & ChrW(225) & "c tr" & ChrW(432) & ChrW(7901) & "ng c" & ChrW(243) & " nh" & ChrW(7853) & "p level (th" & ChrW(7917) & "a kh" & ChrW(244) & "ng c" & ChrW(243) & " nh" & ChrW(227) & "n " & ChrW(273) & ChrW(7875) & " tr" & ChrW(7889) & "ng)"
    c2.Left = x: c2.Top = 280: c2.Width = 350: c2.Height = 16: c2.Value = False
    c2.Font.Name = "Arial": c2.Font.size = 8
    AddPair "L" & ChrW(7899) & "p nh" & ChrW(227) & "n:", "txtLvNhan", "13", x, 230
    AddPair "C" & ChrW(7905) & " ch" & ChrW(7919) & " nh" & ChrW(227) & "n:", "txtCao", "1", x, 254

    ' Tu dien CSDL theo ten file .dgn dang mo (dc01.dgn -> dc01.txt)
    Me.Controls("txtPath").Text = CsdlMacDinh()

    Dim b1 As Object, b2 As Object
    Set b1 = Me.Controls.Add("Forms.CommandButton.1", "cmdOK", True)
    b1.Caption = "Ch" & ChrW(7845) & "p nh" & ChrW(7853) & "n": b1.Left = 170: b1.Top = 306: b1.Width = 95: b1.Height = 26
    b1.Font.Name = "Arial": b1.Font.size = 8
    Set b2 = Me.Controls.Add("Forms.CommandButton.1", "cmdDong", True)
    b2.Caption = ChrW(272) & ChrW(243) & "ng": b2.Left = 275: b2.Top = 306: b2.Width = 80: b2.Height = 26
    b2.Font.Name = "Arial": b2.Font.size = 8
    Dim h1 As clsNutTL, h2 As clsNutTL
    Set h1 = New clsNutTL: Set h1.btn = b1: Set h1.Form = Me: h1.ma = "OK": mNut.Add h1
    Set h2 = New clsNutTL: Set h2.btn = b2: Set h2.Form = Me: h2.ma = "DONG": mNut.Add h2
End Sub

Private Sub AddLabel(ByVal nm As String, ByVal cap As String, _
                     ByVal x As Single, ByVal y As Single, ByVal w As Single)
    Dim c As Object
    Set c = Me.Controls.Add("Forms.Label.1", nm, True)
    c.Caption = cap: c.Left = x: c.Top = y: c.Width = w: c.Height = 14
    c.Font.Name = "Arial": c.Font.size = 8
End Sub

Private Sub AddText(ByVal nm As String, ByVal txt As String, _
                    ByVal x As Single, ByVal y As Single, ByVal w As Single)
    Dim c As Object
    Set c = Me.Controls.Add("Forms.TextBox.1", nm, True)
    c.Text = txt: c.Left = x: c.Top = y: c.Width = w: c.Height = 16
    c.Font.Name = "Arial": c.Font.size = 8
End Sub

Private Sub AddPair(ByVal cap As String, ByVal nm As String, ByVal txt As String, _
                    ByVal x As Single, ByVal y As Single)
    AddLabel "lbl_" & nm, cap, x, y + 2, 90
    Dim c As Object
    Set c = Me.Controls.Add("Forms.TextBox.1", nm, True)
    c.Text = txt: c.Left = x + 95: c.Top = y: c.Width = 120: c.Height = 16
    c.Font.Name = "Arial": c.Font.size = 8
End Sub

Public Sub XuLyNut(ByVal ma As String)
    If ma = "DONG" Then Unload Me: Exit Sub
    Dim i As Long, coLv As Boolean, nm As Variant
    For Each nm In Array("txtLvSo", "txtLvTo", "txtLvLoai", "txtLvChu", "txtLvDC")
        If Len(Trim$(Me.Controls(nm).Text)) > 0 Then coLv = True
    Next nm
    If Not coLv Then
        DC_ThongBao "Ch" & ChrW(432) & "a nh" & ChrW(7853) & "p level n" & ChrW(224) & "o (s" & ChrW(7889) & " hi" & ChrW(7879) & "u th" & ChrW(7917) & "a / t" & ChrW(7901) & " / lo" & ChrW(7841) & "i " & ChrW(273) & ChrW(7845) & "t / t" & ChrW(234) & "n ch" & ChrW(7911) & " / " & ChrW(273) & ChrW(7883) & "a ch" & ChrW(7881) & ").", "G" & ChrW(225) & "n th" & ChrW(244) & "ng tin", vbExclamation
        Exit Sub
    End If
    Me.Hide
    On Error GoTo Loi
    ChayGanTT Me.Controls("txtPath").Text, Me.Controls("txtLvSo").Text, _
              Me.Controls("txtLvTo").Text, Me.Controls("txtLvLoai").Text, _
              Me.Controls("txtLvChu").Text, Me.Controls("txtLvDC").Text, _
              Me.Controls("txtLvNhan").Text, val(Me.Controls("txtCao").Text), _
              Me.Controls("chkVe").Value, Me.Controls("chkXoaCu").Value
    Me.Show vbModeless
    Exit Sub
Loi:
    Me.Show vbModeless
    DC_ThongBao "L" & ChrW(7895) & "i khi g" & ChrW(225) & "n th" & ChrW(244) & "ng tin: " & Err.Description, "G" & ChrW(225) & "n th" & ChrW(244) & "ng tin", vbCritical
End Sub

Attribute VB_Name = "frmGioiThieu"
Attribute VB_Base = "0{AFB269FC-478A-455E-8ECB-849DB41297A9}{EC81D18E-32B2-464A-9F75-511826B2722D}"
Attribute VB_GlobalNameSpace = False
Attribute VB_Creatable = False
Attribute VB_PredeclaredId = True
Attribute VB_Exposed = False
Attribute VB_TemplateDerived = False
Attribute VB_Customizable = False
'============================================================
' frmGioiThieu - Hop "Gioi thieu" dung Label font Arial
'   Tieu de thanh (title bar) de ASCII de khoi "?".
'============================================================
Option Explicit

Private mNut As New Collection

Private Sub UserForm_Initialize()
    Me.Caption = "Gioi thieu"
    Me.Width = 410
    Me.Height = 198

    Dim l1 As Object
    Set l1 = Me.Controls.Add("Forms.Label.1", "lblTen", True)
    l1.Caption = ChrW(272) & ChrW(7882) & "A CH" & ChrW(205) & "NH VL - Phi" & ChrW(234) & "n b" & ChrW(7843) & "n " & DC_PhienBan()
    l1.Left = 12: l1.Top = 12: l1.Width = 382: l1.Height = 18
    l1.Font.Name = "Arial": l1.Font.size = 11: l1.Font.Bold = True
    l1.TextAlign = 2   ' center

    Dim lDv As Object
    Set lDv = Me.Controls.Add("Forms.Label.1", "lblDonVi", True)
    lDv.Caption = "V" & ChrW(259) & "n ph" & ChrW(242) & "ng " & ChrW(273) & ChrW(259) & "ng k" & ChrW(253) & " " & ChrW(273) & ChrW(7845) & "t " & ChrW(273) & "ai t" & ChrW(7881) & "nh V" & ChrW(297) & "nh Long - Ph" & ChrW(242) & "ng c" & ChrW(244) & "ng ngh" & ChrW(7879) & " d" & ChrW(7919) & " li" & ChrW(7879) & "u"
    lDv.Left = 12: lDv.Top = 34: lDv.Width = 382: lDv.Height = 16
    lDv.Font.Name = "Arial": lDv.Font.size = 9: lDv.Font.Bold = True
    lDv.ForeColor = &H800000           ' xanh dam
    lDv.TextAlign = 2

    Dim L2 As Object
    Set L2 = Me.Controls.Add("Forms.Label.1", "lblND", True)
    L2.Caption = "C" & ChrW(244) & "ng c" & ChrW(7909) & " t" & ChrW(7841) & "o v" & ChrW(249) & "ng, xu" & ChrW(7845) & "t tr" & ChrW(237) & "ch l" & ChrW(7909) & "c mi" & ChrW(7877) & "n ph" & ChrW(237) & "."
    L2.Left = 12: L2.Top = 58: L2.Width = 382: L2.Height = 16
    L2.Font.Name = "Arial": L2.Font.size = 9
    L2.TextAlign = 2

    Dim lNote As Object
    Set lNote = Me.Controls.Add("Forms.Label.1", "lblNote", True)
    lNote.Caption = "(Anh, Ch" & ChrW(7883) & " t" & ChrW(7843) & "i v" & ChrW(7873) & " vi" & ChrW(7871) & "t l" & ChrW(7841) & "i ph" & ChrW(249) & " h" & ChrW(7907) & "p cho " & ChrW(273) & ChrW(417) & "n v" & ChrW(7883) & " m" & ChrW(236) & "nh)"
    lNote.Left = 12: lNote.Top = 78: lNote.Width = 382: lNote.Height = 16
    lNote.Font.Name = "Arial": lNote.Font.size = 8: lNote.Font.Italic = True
    lNote.TextAlign = 2

    Dim l3 As Object
    Set l3 = Me.Controls.Add("Forms.Label.1", "lblMail", True)
    l3.Caption = "Email g" & ChrW(243) & "p " & ChrW(253) & ": lehoangtuat@hotmail.com"
    l3.Left = 12: l3.Top = 102: l3.Width = 382: l3.Height = 16
    l3.Font.Name = "Arial": l3.Font.size = 9
    l3.TextAlign = 2

    Dim b As Object
    Set b = Me.Controls.Add("Forms.CommandButton.1", "cmdOK", True)
    b.Caption = "OK": b.Left = 167: b.Top = 130: b.Width = 76: b.Height = 26
    b.Font.Name = "Arial": b.Font.size = 8
    Dim hd As clsNutTL
    Set hd = New clsNutTL
    Set hd.btn = b: Set hd.Form = Me: hd.ma = "OK"
    mNut.Add hd
End Sub

Public Sub XuLyNut(ByVal ma As String)
    If ma = "OK" Then Unload Me
End Sub

Attribute VB_Name = "frmKiemVung"
Attribute VB_Base = "0{B5F932DF-AADA-4869-977D-E6C738EAA81E}{8FEA4151-E482-4F81-9647-5E9BC518A7C8}"
Attribute VB_GlobalNameSpace = False
Attribute VB_Creatable = False
Attribute VB_PredeclaredId = True
Attribute VB_Exposed = False
Attribute VB_TemplateDerived = False
Attribute VB_Customizable = False
'============================================================
' frmKiemVung - Kiem tra vung thua (giao nop TW): moi vung 1 so thua / 1 loai dat / 1 dien tich
'   Can: modKiemVung, clsNutTL, clsListEvent, modCuonChuot. Mo bang DC_MoFormTuTao.
'============================================================
Option Explicit

Private mNut As New Collection
Private mLst As clsListEvent
Private mCuon As Object
Private mTec As Object

Private Sub UserForm_Initialize()
    Dim c As Object
    Me.Caption = "Kiem tra vung thua (giao nop TW)"
    Me.Width = 430: Me.Height = 426
    Me.Font.Name = "Arial": Me.Font.size = 8

    Nhan "L" & ChrW(7899) & "p ranh th" & ChrW(7917) & "a (c" & ChrW(225) & "ch nhau d" & ChrW(7845) & "u ph" & ChrW(7849) & "y):", 8, 10, 170
    o "txtRanh", DC_DocCauHinh("KV_RANH", "10,23,31"), 180, 8, 100
    Nhan "Snap (m):", 290, 10, 44
    o "txtSnap", DC_DocCauHinh("KV_SNAP2", "0.001"), 336, 8, 44

    Nhan "L" & ChrW(7899) & "p s" & ChrW(7889) & " th" & ChrW(7917) & "a:", 8, 34, 60
    o "txtSo", DC_DocCauHinh("KV_SO", "13"), 70, 32, 34
    Nhan "L" & ChrW(7899) & "p lo" & ChrW(7841) & "i " & ChrW(273) & ChrW(7845) & "t:", 116, 34, 62
    o "txtLD", DC_DocCauHinh("KV_LD", "2"), 180, 32, 34
    Nhan "L" & ChrW(7899) & "p di" & ChrW(7879) & "n t" & ChrW(237) & "ch:", 226, 34, 66
    o "txtDT", DC_DocCauHinh("KV_DT", "4"), 294, 32, 34

    Set c = Me.Controls.Add("Forms.CheckBox.1", "chkGiao", True)
    c.Caption = "Chia " & ChrW(273) & "o" & ChrW(7841) & "n t" & ChrW(7841) & "i giao " & ChrW(273) & "i" & ChrW(7875) & "m (ranh c" & ChrW(7855) & "t nhau kh" & ChrW(244) & "ng c" & ChrW(243) & " n" & ChrW(250) & "t)"
    c.Left = 8: c.Top = 54: c.Width = 290: c.Height = 16: c.Font.Name = "Arial": c.Font.size = 8
    c.Value = (DC_DocCauHinh("KV_GIAO", "1") = "1")

    ThemNut "DAULECH", "D" & ChrW(242) & " " & ChrW(273) & ChrW(7847) & "u ranh l" & ChrW(7879) & "ch", 300, 50, 112
    ThemNut "KIEM", "Ki" & ChrW(7875) & "m tra", 8, 74, 90
    ThemNut "VEDAU", "V" & ChrW(7869) & " d" & ChrW(7845) & "u l" & ChrW(7895) & "i", 104, 74, 90
    ThemNut "XOADAU", "X" & ChrW(243) & "a d" & ChrW(7845) & "u l" & ChrW(7895) & "i", 200, 74, 90
    Nhan "L" & ChrW(7899) & "p d" & ChrW(7845) & "u:", 300, 78, 40
    o "txtLvLoi", DC_DocCauHinh("KV_LVLOI", "62"), 342, 74, 36

    Nhan "L" & ChrW(7899) & "p ngu" & ChrW(7891) & "n nh" & ChrW(227) & "n:", 8, 104, 70
    o "txtNguon", DC_DocCauHinh("PN_NGUON", "13,29,4,63,1"), 80, 102, 100
    Nhan "L" & ChrW(7899) & "p l" & ChrW(432) & "u ch" & ChrW(7919) & " g" & ChrW(7889) & "c:", 186, 104, 70
    o "txtLuu", DC_DocCauHinh("PN_LUU", "60"), 258, 102, 34
    ThemNut "PHANNHAN", "Ph" & ChrW(226) & "n nh" & ChrW(227) & "n theo th" & ChrW(7917) & "a", 300, 98, 112
    Set c = Me.Controls.Add("Forms.Label.1", "lblTom", True)
    c.Left = 8: c.Top = 128: c.Width = 404: c.Height = 64
    c.Font.Name = "Arial": c.Font.size = 8: c.ForeColor = rgB(160, 0, 0)
    c.Caption = "B" & ChrW(7845) & "m Ki" & ChrW(7875) & "m tra. M" & ChrW(7895) & "i v" & ChrW(249) & "ng th" & ChrW(7917) & "a ph" & ChrW(7843) & "i c" & ChrW(243) & " " & ChrW(273) & ChrW(250) & "ng 1 s" & ChrW(7889) & " hi" & ChrW(7879) & "u th" & ChrW(7917) & "a, 1 lo" & ChrW(7841) & "i " & ChrW(273) & ChrW(7845) & "t, 1 di" & ChrW(7879) & "n t" & ChrW(237) & "ch."

    Nhan "STT", 8, 196, 28
    Nhan "L" & ChrW(7895) & "i c" & ChrW(7911) & "a v" & ChrW(249) & "ng th" & ChrW(7917) & "a", 38, 196, 240
    Nhan "S" & ChrW(7889) & " th" & ChrW(7917) & "a trong v" & ChrW(249) & "ng", 300, 196, 110
    Dim lst As Object
    Set lst = Me.Controls.Add("Forms.ListBox.1", "lstLoi", True)
    lst.Left = 8: lst.Top = 210: lst.Width = 404: lst.Height = 150
    lst.ColumnCount = 3: lst.ColumnWidths = "30;260;110"
    lst.Font.Name = "Arial": lst.Font.size = 8
    Set mLst = New clsListEvent
    Set mLst.lst = lst
    Set mLst.Form = Me
    Set mCuon = DC_GanCuon(lst, Me)

    Nhan "B" & ChrW(7845) & "m 1 d" & ChrW(242) & "ng " & ChrW(273) & ChrW(7875) & " ph" & ChrW(243) & "ng t" & ChrW(7899) & "i v" & ChrW(249) & "ng l" & ChrW(7895) & "i. Nh" & ChrW(7899) & " X" & ChrW(243) & "a d" & ChrW(7845) & "u l" & ChrW(7895) & "i tr" & ChrW(432) & ChrW(7899) & "c khi giao n" & ChrW(7897) & "p.", 8, 368, 300
    ThemNut "DONG", ChrW(272) & ChrW(243) & "ng", 330, 364, 82
End Sub

Public Sub XuLyNut(ByVal ma As String)
    Dim n As Long, tom As String, i As Long, a As Variant, lst As Object, td As String
    td = "Ki" & ChrW(7875) & "m tra v" & ChrW(249) & "ng th" & ChrW(7917) & "a"
    Select Case ma
        Case "DONG"
TatDanhDau:             Unload Me
        Case "KIEM"
            Luu
            Me.Controls("lblTom").Caption = ChrW(272) & "ang ki" & ChrW(7875) & "m tra ..."
            DoEvents
            n = KV_KiemTra(Me.Controls("txtRanh").Text, Me.Controls("txtSo").Text, Me.Controls("txtLD").Text, _
                           Me.Controls("txtDT").Text, val(Replace(Me.Controls("txtSnap").Text, ",", ".")), _
                           CBool(Me.Controls("chkGiao").Value), tom)
            Me.Controls("lblTom").Caption = tom
            Set lst = Me.Controls("lstLoi")
            lst.Clear
            If Not KV_DsLoi Is Nothing Then
                For i = 1 To KV_DsLoi.Count
                    a = KV_DsLoi.Item(i)
                    lst.AddItem CStr(i)
                    lst.List(lst.ListCount - 1, 1) = a(1)
                    lst.List(lst.ListCount - 1, 2) = a(2)
                Next i
            End If
        Case "PHANNHAN"
            Luu
            Me.Controls("lblTom").Caption = ChrW(272) & "ang ph" & ChrW(226) & "n nh" & ChrW(227) & "n theo th" & ChrW(7917) & "a ..."
            DoEvents
            n = PN_Chay(Me.Controls("txtRanh").Text, Me.Controls("txtNguon").Text, Me.Controls("txtSo").Text, _
                        Me.Controls("txtLD").Text, Me.Controls("txtDT").Text, Me.Controls("txtLuu").Text, _
                        val(Replace(Me.Controls("txtSnap").Text, ",", ".")), CBool(Me.Controls("chkGiao").Value), tom)
            Me.Controls("lblTom").Caption = tom
            Set lst = Me.Controls("lstLoi")
            lst.Clear
            If Not KV_DsLoi Is Nothing Then
                For i = 1 To KV_DsLoi.Count
                    a = KV_DsLoi.Item(i)
                    lst.AddItem CStr(i)
                    lst.List(lst.ListCount - 1, 1) = a(1)
                    lst.List(lst.ListCount - 1, 2) = a(2)
                Next i
            End If
        Case "DAULECH"
            Luu
            Me.Controls("lblTom").Caption = ChrW(272) & "ang d" & ChrW(242) & " " & ChrW(273) & ChrW(7847) & "u ranh l" & ChrW(7879) & "ch ..."
            DoEvents
            n = KV_DoDauLech(Me.Controls("txtRanh").Text, 0.001, tom)
            Me.Controls("lblTom").Caption = tom
            Set lst = Me.Controls("lstLoi")
            lst.Clear
            If Not KV_DsLoi Is Nothing Then
                For i = 1 To KV_DsLoi.Count
                    a = KV_DsLoi.Item(i)
                    lst.AddItem CStr(i)
                    lst.List(lst.ListCount - 1, 1) = a(1)
                    lst.List(lst.ListCount - 1, 2) = a(2)
                Next i
            End If
        Case "VEDAU"
            If KV_DsLoi Is Nothing Then DC_ThongBao "B" & ChrW(7845) & "m Ki" & ChrW(7875) & "m tra tr" & ChrW(432) & ChrW(7899) & "c.", td, vbExclamation: Exit Sub
            Luu
            n = KV_VeDauLoi(Me.Controls("txtLvLoi").Text, 1#)
            DC_ThongBao ChrW(272) & ChrW(227) & " v" & ChrW(7869) & " " & n & " d" & ChrW(7845) & "u l" & ChrW(7895) & "i (kh" & ChrW(7889) & "i LOIVUNG, m" & ChrW(224) & "u " & ChrW(273) & ChrW(7887) & ")." & vbCrLf & "Nh" & ChrW(7899) & " X" & ChrW(243) & "a d" & ChrW(7845) & "u l" & ChrW(7895) & "i tr" & ChrW(432) & ChrW(7899) & "c khi giao n" & ChrW(7897) & "p.", td
        Case "XOADAU"
            n = KV_XoaDauLoi()
            DC_ThongBao ChrW(272) & ChrW(227) & " x" & ChrW(243) & "a " & n & " d" & ChrW(7845) & "u l" & ChrW(7895) & "i.", td
    End Select
End Sub

' Bam 1 dong -> zoom + to do vung
Public Sub DongChon()
    Dim r As Long, a As Variant, v As clsVung, rg() As Double, x1 As Double, y1 As Double, x2 As Double, y2 As Double, d As Double
    r = Me.Controls("lstLoi").ListIndex
    If r < 0 Or KV_DsLoi Is Nothing Then Exit Sub
    If r + 1 > KV_DsLoi.Count Then Exit Sub
    a = KV_DsLoi.Item(r + 1): Set v = a(0)
    On Error Resume Next
    rg = v.ring
    BaoRing rg, x1, y1, x2, y2
    d = x2 - x1: If y2 - y1 > d Then d = y2 - y1
    If d < 20 Then d = 20
    DC_ZoomVung (x1 + x2) / 2 - d * 1.5, (y1 + y2) / 2 - d * 1.5, (x1 + x2) / 2 + d * 1.5, (y1 + y2) / 2 + d * 1.5
    DanhDau rg
End Sub

Private Sub DanhDau(rg() As Double)
    Dim pts() As Point3d, i As Long, n As Long, el As Element
    TatDanhDau
    On Error Resume Next
    n = UBound(rg, 1)
    ReDim pts(0 To n)
    For i = 0 To n
        pts(i).x = rg(i, 0): pts(i).y = rg(i, 1): pts(i).Z = 0#
    Next i
    Set el = CreateShapeElement1(Nothing, pts)
    If el Is Nothing Then Exit Sub
    el.color = 3: el.LineWeight = 5
    mTec.Add CreateTransientElementContainer1(el, 0, 255, msdDrawingModeNormal)
End Sub

Private Sub TatDanhDau()
    Dim i As Long
    On Error Resume Next
    If mTec Is Nothing Then Set mTec = New Collection: Exit Sub
    For i = mTec.Count To 1 Step -1
        mTec.Item(i).Reset
        mTec.Remove i
    Next i
End Sub

Private Sub Luu()
    DC_GhiCauHinh "KV_RANH", Me.Controls("txtRanh").Text
    DC_GhiCauHinh "KV_SNAP2", Me.Controls("txtSnap").Text
    DC_GhiCauHinh "KV_SO", Me.Controls("txtSo").Text
    DC_GhiCauHinh "KV_LD", Me.Controls("txtLD").Text
    DC_GhiCauHinh "KV_DT", Me.Controls("txtDT").Text
    DC_GhiCauHinh "KV_GIAO", IIf(Me.Controls("chkGiao").Value, "1", "0")
    DC_GhiCauHinh "KV_LVLOI", Me.Controls("txtLvLoi").Text
    DC_GhiCauHinh "PN_NGUON", Me.Controls("txtNguon").Text
    DC_GhiCauHinh "PN_LUU", Me.Controls("txtLuu").Text
End Sub

Private Sub Nhan(ByVal cap As String, ByVal x As Single, ByVal y As Single, ByVal w As Single)
    Dim c As Object
    Set c = Me.Controls.Add("Forms.Label.1")
    c.Caption = cap: c.Left = x: c.Top = y: c.Width = w: c.Height = 12
    c.Font.Name = "Arial": c.Font.size = 8
End Sub

Private Sub o(ByVal nm As String, ByVal gt As String, ByVal x As Single, ByVal y As Single, ByVal w As Single)
    Dim c As Object
    Set c = Me.Controls.Add("Forms.TextBox.1", nm, True)
    c.Left = x: c.Top = y: c.Width = w: c.Height = 16
    c.Font.Name = "Arial": c.Font.size = 8
    c.Text = gt
End Sub

Private Sub ThemNut(ByVal ma As String, ByVal cap As String, ByVal x As Single, ByVal y As Single, ByVal w As Single)
    Dim b As Object, hd As clsNutTL
    Set b = Me.Controls.Add("Forms.CommandButton.1", "cmd" & ma, True)
    b.Caption = cap: b.Left = x: b.Top = y: b.Width = w: b.Height = 22
    b.Font.Name = "Arial": b.Font.size = 8
    Set hd = New clsNutTL
    Set hd.btn = b: Set hd.Form = Me: hd.ma = ma
    mNut.Add hd
End Sub

Private Sub UserForm_Terminate()
    TatDanhDau
    DC_CuonTat
End Sub

Attribute VB_Name = "frmTachLop"
Attribute VB_Base = "0{9EFE804E-612D-4398-B564-FE440FDB1BE7}{C29150D3-1E88-40A3-B7D0-DCCCAD234CC9}"
Attribute VB_GlobalNameSpace = False
Attribute VB_Creatable = False
Attribute VB_PredeclaredId = True
Attribute VB_Exposed = False
Attribute VB_TemplateDerived = False
Attribute VB_Customizable = False
'============================================================
' frmTachLop - Tach lop nhan (loai dat / so thua / dien tich)
'   1 file hien tai: dem truoc -> hoi -> chuyen (co "chi chu dang chon").
'   Nhieu file (to ban do / thu muc): mo ngam tung file -> chuyen -> Save.
'   Can: modTachLop, modConvertFont (chon file/thu muc), clsNutTL, modCauHinh, modMenuDC
'============================================================
Option Explicit
' SUA 28/10: lan con chuot cuon ListBox (modCuonChuot)
Private mCuon0 As Object

Private mNut As New Collection
Private mDs As Object           ' LCase(path) -> True (chong trung)
Private mDangChay As Boolean

Private Sub UserForm_Initialize()
    Me.Caption = "Tach lop nhan thua"
    Me.Font.Name = "Arial"
    Me.Font.size = 8
    Me.Width = 492
    Me.Height = 352
    Set mDs = CreateObject("Scripting.Dictionary")

    Dim tg As Object
    Set tg = Me.Controls.Add("Forms.Label.1", "lblTieuDe", True)
    tg.Caption = "T" & ChrW(193) & "CH L" & ChrW(7898) & "P NH" & ChrW(195) & "N TH" & ChrW(7916) & "A (ch" & ChrW(7919) & " chung 1 l" & ChrW(7899) & "p " & ChrW(8594) & " lo" & ChrW(7841) & "i " & ChrW(273) & ChrW(7845) & "t / s" & ChrW(7889) & " th" & ChrW(7917) & "a / di" & ChrW(7879) & "n t" & ChrW(237) & "ch)"
    tg.Left = 6: tg.Top = 6: tg.Width = 470: tg.Height = 14
    tg.Font.Name = "Arial": tg.Font.size = 8: tg.Font.Bold = True

    ThemCot "cboNguon", "L" & ChrW(7899) & "p c" & ChrW(7847) & "n t" & ChrW(225) & "ch", 6, DC_DocCauHinh("TLOP_NGUON", "")
    ThemCot "cboLD", "L" & ChrW(7899) & "p lo" & ChrW(7841) & "i " & ChrW(273) & ChrW(7845) & "t", 126, DC_DocCauHinh("TLOP_LD", "")
    ThemCot "cboST", "L" & ChrW(7899) & "p s" & ChrW(7889) & " th" & ChrW(7917) & "a", 246, DC_DocCauHinh("TLOP_ST", "")
    ThemCot "cboDT", "L" & ChrW(7899) & "p di" & ChrW(7879) & "n t" & ChrW(237) & "ch", 366, DC_DocCauHinh("TLOP_DT", "")

    Dim ck As Object
    Set ck = Me.Controls.Add("Forms.CheckBox.1", "chkChon", True)
    ck.Caption = "Ch" & ChrW(7881) & " x" & ChrW(7917) & " l" & ChrW(253) & " ch" & ChrW(7919) & " " & ChrW(273) & "ang ch" & ChrW(7885) & "n (1 file hi" & ChrW(7879) & "n t" & ChrW(7841) & "i)"
    ck.Left = 6: ck.Top = 64: ck.Width = 158: ck.Height = 16
    ck.Font.Name = "Arial": ck.Font.size = 8

    Dim cb As Object
    Set cb = Me.Controls.Add("Forms.CheckBox.1", "chkBak", True)
    cb.Caption = "Sao l" & ChrW(432) & "u .bak"
    cb.Left = 386: cb.Top = 64: cb.Width = 94: cb.Height = 16
    cb.Font.Name = "Arial": cb.Font.size = 8
    cb.Value = (DC_DocCauHinh("TLOP_BAK", "1") = "1")
    cb.ControlTipText = "Ch" & ChrW(233) & "p file g" & ChrW(7889) & "c th" & ChrW(224) & "nh <t" & ChrW(234) & "n>.dgn.bak tr" & ChrW(432) & ChrW(7899) & "c khi s" & ChrW(7917) & "a"

    ' SUA 25/10: pha chu gop "LUC 766/3860,9" -> 3 chu rieng
    ThemNut "TACHCHU", "Ph" & ChrW(225) & " ch" & ChrW(7919) & " g" & ChrW(7897) & "p", "Ch" & ChrW(7919) & " ghi chung 1 d" & ChrW(242) & "ng (vd LUC 766/3860,9): t" & ChrW(225) & "ch th" & ChrW(224) & "nh lo" & ChrW(7841) & "i " & ChrW(273) & ChrW(7845) & "t / s" & ChrW(7889) & " th" & ChrW(7917) & "a / di" & ChrW(7879) & "n t" & ChrW(237) & "ch ri" & ChrW(234) & "ng (gi" & ChrW(7919) & " v" & ChrW(7883) & " tr" & ChrW(237) & ", c" & ChrW(7905) & ", g" & ChrW(243) & "c xoay) - l" & ChrW(224) & "m tr" & ChrW(432) & ChrW(7899) & "c khi T" & ChrW(225) & "ch l" & ChrW(7899) & "p", 166, 61, 96
    ThemNut "PHAKHOI", "Ph" & ChrW(225) & " kh" & ChrW(7889) & "i ch" & ChrW(7919), "Ph" & ChrW(225) & " c" & ChrW(225) & "c kh" & ChrW(7889) & "i (cell) c" & ChrW(243) & " ch" & ChrW(7919) & " tr" & ChrW(234) & "n l" & ChrW(7899) & "p c" & ChrW(7847) & "n t" & ChrW(225) & "ch th" & ChrW(224) & "nh ch" & ChrW(7919) & " r" & ChrW(7901) & "i (nh" & ChrW(432) & " Drop Element) - l" & ChrW(224) & "m tr" & ChrW(432) & ChrW(7899) & "c khi T" & ChrW(225) & "ch l" & ChrW(7899) & "p", 266, 61, 112

    ' --- nut them / bot to ban do
    Dim x As Single: x = 6
    ThemNut "FILE", "+ Th" & ChrW(234) & "m t" & ChrW(7901), "Th" & ChrW(234) & "m c" & ChrW(225) & "c t" & ChrW(7901) & " b" & ChrW(7843) & "n " & ChrW(273) & ChrW(7891) & " (.dgn)", x, 84, 70: x = x + 74
    ThemNut "THUMUC", "+ Th" & ChrW(432) & " m" & ChrW(7909) & "c", "Th" & ChrW(234) & "m th" & ChrW(432) & " m" & ChrW(7909) & "c ch" & ChrW(7913) & "a b" & ChrW(7843) & "n " & ChrW(273) & ChrW(7891), x, 84, 64: x = x + 68
    ThemNut "THUMUCCON", "+ C" & ChrW(7843) & " th" & ChrW(432) & " m" & ChrW(7909) & "c con", "Th" & ChrW(234) & "m b" & ChrW(7843) & "n " & ChrW(273) & ChrW(7891) & " c" & ChrW(7843) & " trong th" & ChrW(432) & " m" & ChrW(7909) & "c con", x, 84, 88: x = x + 92
    ThemNut "HIENTAI", "+ File hi" & ChrW(7879) & "n t" & ChrW(7841) & "i", "Th" & ChrW(234) & "m file b" & ChrW(7843) & "n " & ChrW(273) & ChrW(7891) & " hi" & ChrW(7879) & "n t" & ChrW(7841) & "i", x, 84, 78: x = x + 82
    ThemNut "BOCHON", "B" & ChrW(7887) & " file ch" & ChrW(7885) & "n", "B" & ChrW(7887) & " c" & ChrW(225) & "c file " & ChrW(273) & "ang ch" & ChrW(7885) & "n kh" & ChrW(7887) & "i danh s" & ChrW(225) & "ch", x, 84, 72: x = x + 76
    ThemNut "XOAHET", "X" & ChrW(243) & "a h" & ChrW(7871) & "t", "X" & ChrW(243) & "a to" & ChrW(224) & "n b" & ChrW(7897) & " danh s" & ChrW(225) & "ch files", x, 84, 60

    Dim ls As Object
    Set ls = Me.Controls.Add("Forms.ListBox.1", "lstFile", True)
    Set mCuon0 = DC_GanCuon(ls, Me)     ' SUA 28/10: lan chuot cuon danh sach
    ls.Left = 6: ls.Top = 108: ls.Width = 474: ls.Height = 120
    ls.Font.Name = "Arial": ls.Font.size = 8
    ls.ColumnCount = 2: ls.ColumnWidths = "330;138"
    ls.MultiSelect = 2

    Dim s1 As Object, s2 As Object
    Set s1 = Me.Controls.Add("Forms.Label.1", "lblDem", True)
    s1.Left = 6: s1.Top = 232: s1.Width = 52: s1.Height = 14
    s1.Font.Name = "Arial": s1.Font.size = 8: s1.SpecialEffect = 2
    Set s2 = Me.Controls.Add("Forms.Label.1", "lblPath", True)
    s2.Left = 62: s2.Top = 232: s2.Width = 418: s2.Height = 14
    s2.Font.Name = "Arial": s2.Font.size = 8: s2.SpecialEffect = 2

    Dim gc As Object
    Set gc = Me.Controls.Add("Forms.Label.1", "lblGhiChu", True)
    gc.Caption = "C" & ChrW(243) & " ch" & ChrW(7919) & " c" & ChrW(225) & "i (LUK, ONT...) = lo" & ChrW(7841) & "i " & ChrW(273) & ChrW(7845) & "t; ch" & ChrW(7881) & " ch" & ChrW(7919) & " s" & ChrW(7889) & " (2248) = s" & ChrW(7889) & " th" & ChrW(7917) & "a; s" & ChrW(7889) & " c" & ChrW(243) & " d" & ChrW(7845) & "u ph" & ChrW(7849) & "y (4846,2) = di" & ChrW(7879) & "n t" & ChrW(237) & "ch." & vbCrLf & _
                 ChrW(272) & ChrW(7875) & " tr" & ChrW(7889) & "ng " & ChrW(244) & " n" & ChrW(224) & "o th" & ChrW(236) & " kh" & ChrW(244) & "ng t" & ChrW(225) & "ch lo" & ChrW(7841) & "i " & ChrW(273) & ChrW(243) & ". Level ch" & ChrW(432) & "a c" & ChrW(243) & " th" & ChrW(236) & " t" & ChrW(7921) & " t" & ChrW(7841) & "o. Nhi" & ChrW(7873) & "u file: t" & ChrW(7921) & " m" & ChrW(7903) & ", t" & ChrW(225) & "ch, l" & ChrW(432) & "u t" & ChrW(7915) & "ng t" & ChrW(7901) & "."
    gc.Left = 6: gc.Top = 252: gc.Width = 474: gc.Height = 26
    gc.Font.Name = "Arial": gc.Font.size = 8: gc.Font.Italic = True

    ' SUA 05/11: xoa chu trung + o sai so
    ThemNut "XOATRUNG", "X" & ChrW(243) & "a ch" & ChrW(7919) & " tr" & ChrW(249) & "ng", "X" & ChrW(243) & "a ch" & ChrW(7919) & " c" & ChrW(249) & "ng n" & ChrW(7897) & "i dung, c" & ChrW(249) & "ng l" & ChrW(7899) & "p n" & ChrW(7857) & "m ch" & ChrW(7891) & "ng l" & ChrW(234) & "n nhau (copy/d" & ChrW(225) & "n 2 l" & ChrW(7847) & "n) - gi" & ChrW(7919) & " l" & ChrW(7841) & "i 1 ch" & ChrW(7919), 6, 288, 104
    Dim lt As Object, tt As Object
    Set lt = Me.Controls.Add("Forms.Label.1", "lblTrung", True)
    lt.Caption = "Sai s" & ChrW(7889) & " (m):": lt.Left = 116: lt.Top = 292: lt.Width = 52: lt.Height = 14
    lt.Font.Name = "Arial": lt.Font.size = 8
    Set tt = Me.Controls.Add("Forms.TextBox.1", "txtTrung", True)
    tt.Left = 168: tt.Top = 289: tt.Width = 40: tt.Height = 18
    tt.Font.Name = "Arial": tt.Font.size = 8
    tt.Text = DC_DocCauHinh("TLOP_TRUNG", "0.2")
    ThemNut "TACH", "T" & ChrW(225) & "ch l" & ChrW(7899) & "p", "", 290, 286, 92
    ThemNut "DONG", ChrW(272) & ChrW(243) & "ng", "", 388, 286, 92

    On Error Resume Next
    ThemFile ActiveDesignFile.FullName
    On Error GoTo 0
    CapNhatDem
End Sub

Private Sub ThemCot(ByVal nm As String, ByVal cap As String, ByVal x As Single, ByVal gt As String)
    Dim L As Object, c As Object
    Set L = Me.Controls.Add("Forms.Label.1", "lbl" & nm, True)
    L.Caption = cap: L.Left = x: L.Top = 26: L.Width = 114: L.Height = 12
    L.Font.Name = "Arial": L.Font.size = 8
    Set c = Me.Controls.Add("Forms.ComboBox.1", nm, True)
    c.Left = x: c.Top = 40: c.Width = 114: c.Height = 18
    c.Font.Name = "Arial": c.Font.size = 8
    NapLevel c
    c.Text = gt
End Sub

Private Sub NapLevel(ByVal cL As Object)
    Dim lv As Level, n As Long, i As Long, j As Long, t As Long, ts As String
    Dim so() As Long, ten() As String
    On Error Resume Next
    ReDim so(0 To 0): ReDim ten(0 To 0)
    For Each lv In ActiveDesignFile.Levels
        n = n + 1
        ReDim Preserve so(0 To n): ReDim Preserve ten(0 To n)
        so(n) = lv.Number: ten(n) = lv.Name
    Next lv
    For i = 1 To n - 1
        For j = i + 1 To n
            If so(j) < so(i) Then
                t = so(i): so(i) = so(j): so(j) = t
                ts = ten(i): ten(i) = ten(j): ten(j) = ts
            End If
        Next j
    Next i
    For i = 1 To n
        cL.AddItem so(i) & " - " & ten(i)
    Next i
End Sub

Private Sub ThemNut(ByVal ma As String, ByVal cap As String, ByVal tip As String, _
                    ByVal x As Single, ByVal y As Single, ByVal w As Single)
    Dim b As Object, hd As clsNutTL
    Set b = Me.Controls.Add("Forms.CommandButton.1", "cmd" & ma, True)
    b.Caption = cap: b.Left = x: b.Top = y: b.Width = w: b.Height = IIf(ma = "TACH" Or ma = "DONG", 24, 20)
    b.Font.Name = "Arial": b.Font.size = 8
    If Len(tip) > 0 Then b.ControlTipText = tip
    Set hd = New clsNutTL
    Set hd.btn = b: Set hd.Form = Me: hd.ma = ma
    mNut.Add hd
End Sub

Private Function lst() As Object
    Set lst = Me.Controls("lstFile")
End Function

Private Function ThemFile(ByVal p As String) As Boolean
    Dim k As String
    p = Trim$(p)
    If Len(p) = 0 Then Exit Function
    k = LCase$(p)
    If mDs.Exists(k) Then Exit Function
    mDs.Add k, True
    lst.AddItem p
    lst.List(lst.ListCount - 1, 1) = ""
    ThemFile = True
End Function

Private Sub CapNhatDem()
    Me.Controls("lblDem").Caption = " " & lst.ListCount & " file"
    If lst.ListCount = 0 Then Me.Controls("lblPath").Caption = ""
End Sub

Private Sub ThemTuDs(ByVal dS As Collection)
    Dim i As Long, n As Long
    For i = 1 To dS.Count
        If ThemFile(CStr(dS.Item(i))) Then n = n + 1
    Next i
    CapNhatDem
    Me.Controls("lblPath").Caption = " " & ChrW(272) & ChrW(227) & " th" & ChrW(234) & "m " & n & " file."
End Sub

' So level tu o nhap ("13 - Level 13" -> 13 ; trong -> 0)
Private Function SoLv(ByVal nm As String) As Long
    Dim s As String
    s = Trim$(CStr(Me.Controls(nm).Text))
    If Len(s) = 0 Then Exit Function
    SoLv = CLng(val(s))
End Function

Public Sub XuLyNut(ByVal ma As String)
    If mDangChay Then Exit Sub
    Dim dS As Collection, p As String, i As Long
    Select Case ma
    Case "DONG"
        Unload Me
    Case "FILE"
        ThemTuDs CF_ChonNhieuFile()
    Case "THUMUC", "THUMUCCON"
        p = CF_ChonThuMuc(IIf(ma = "THUMUC", "Ch" & ChrW(7885) & "n th" & ChrW(432) & " m" & ChrW(7909) & "c ch" & ChrW(7913) & "a b" & ChrW(7843) & "n " & ChrW(273) & ChrW(7891) & " (*.dgn)", "Ch" & ChrW(7885) & "n th" & ChrW(432) & " m" & ChrW(7909) & "c (l" & ChrW(7845) & "y c" & ChrW(7843) & " th" & ChrW(432) & " m" & ChrW(7909) & "c con)"))
        If Len(p) = 0 Then Exit Sub
        Set dS = New Collection
        Me.Controls("lblPath").Caption = " " & ChrW(272) & "ang t" & ChrW(236) & "m file trong " & p & " ..."
        DoEvents
        CF_GomFileDgn p, (ma = "THUMUCCON"), dS
        ThemTuDs dS
    Case "HIENTAI"
        On Error Resume Next
        p = ActiveDesignFile.FullName
        On Error GoTo 0
        If Len(p) > 0 Then ThemFile p
        CapNhatDem
    Case "BOCHON"
        For i = lst.ListCount - 1 To 0 Step -1
            If lst.Selected(i) Then
                If mDs.Exists(LCase$(lst.List(i, 0))) Then mDs.Remove LCase$(lst.List(i, 0))
                lst.RemoveItem i
            End If
        Next i
        CapNhatDem
    Case "XOAHET"
        lst.Clear
        mDs.RemoveAll
        CapNhatDem
    Case "TACH"
        ChayTach
    Case "PHAKHOI"
        ChayPhaKhoi
    Case "TACHCHU"
        ChayTachChu
    Case "XOATRUNG"
        ChayXoaTrung
    End Select
End Sub

Private Sub ChayTach()
    Dim lvN As Long, lv(1 To 3) As Long, n() As Long, nBo As Long, tong As Long, nDa() As Long
    Dim tieuDe As String, chiChon As Boolean, s As String, bak As Boolean
    Dim nF As Long, i As Long, kq As String, nOK As Long, nLoi As Long, Loi As String
    Dim t1 As Long, t2 As Long, t3 As Long, laHT As Boolean
    tieuDe = "T" & ChrW(225) & "ch l" & ChrW(7899) & "p"
    lvN = SoLv("cboNguon")
    lv(1) = SoLv("cboLD"): lv(2) = SoLv("cboST"): lv(3) = SoLv("cboDT")
    If lvN <= 0 Then
        DC_ThongBao "Ch" & ChrW(432) & "a nh" & ChrW(7853) & "p l" & ChrW(7899) & "p c" & ChrW(7847) & "n t" & ChrW(225) & "ch.", tieuDe, vbExclamation
        Exit Sub
    End If
    If lv(1) <= 0 And lv(2) <= 0 And lv(3) <= 0 Then
        DC_ThongBao "Ch" & ChrW(432) & "a nh" & ChrW(7853) & "p l" & ChrW(7899) & "p " & ChrW(273) & ChrW(237) & "ch n" & ChrW(224) & "o (lo" & ChrW(7841) & "i " & ChrW(273) & ChrW(7845) & "t / s" & ChrW(7889) & " th" & ChrW(7917) & "a / di" & ChrW(7879) & "n t" & ChrW(237) & "ch).", tieuDe, vbExclamation
        Exit Sub
    End If
    nF = lst.ListCount
    If nF = 0 Then
        DC_ThongBao "Danh s" & ChrW(225) & "ch ch" & ChrW(432) & "a c" & ChrW(243) & " t" & ChrW(7901) & " b" & ChrW(7843) & "n " & ChrW(273) & ChrW(7891) & " n" & ChrW(224) & "o.", tieuDe, vbExclamation
        Exit Sub
    End If
    chiChon = CBool(Me.Controls("chkChon").Value)
    bak = CBool(Me.Controls("chkBak").Value)

    DC_GhiCauHinh "TLOP_NGUON", CStr(lvN)
    DC_GhiCauHinh "TLOP_LD", IIf(lv(1) > 0, CStr(lv(1)), "")
    DC_GhiCauHinh "TLOP_ST", IIf(lv(2) > 0, CStr(lv(2)), "")
    DC_GhiCauHinh "TLOP_DT", IIf(lv(3) > 0, CStr(lv(3)), "")
    DC_GhiCauHinh "TLOP_BAK", IIf(bak, "1", "0")

    On Error Resume Next
    laHT = (StrComp(CStr(lst.List(0, 0)), ActiveDesignFile.FullName, vbTextCompare) = 0)
    On Error GoTo 0

    ' ---- 1 file hien tai: dem truoc -> hoi -> chuyen
    If nF = 1 And laHT Then
        tong = TL_Quet(lvN, chiChon, n, nBo)
        If tong = 0 Then
            DC_ThongBao "Kh" & ChrW(244) & "ng t" & ChrW(236) & "m th" & ChrW(7845) & "y ch" & ChrW(7919) & " n" & ChrW(224) & "o c" & ChrW(7847) & "n t" & ChrW(225) & "ch tr" & ChrW(234) & "n l" & ChrW(7899) & "p " & lvN & IIf(chiChon, " (trong c" & ChrW(225) & "c ch" & ChrW(7919) & " " & ChrW(273) & "ang ch" & ChrW(7885) & "n).", "."), tieuDe, vbExclamation
            Exit Sub
        End If
        s = "L" & ChrW(7899) & "p " & lvN & " c" & ChrW(243) & ":" & vbCrLf & _
            "  - Lo" & ChrW(7841) & "i " & ChrW(273) & ChrW(7845) & "t: " & n(1) & IIf(lv(1) > 0, " " & ChrW(8594) & " l" & ChrW(7899) & "p " & lv(1), " (kh" & ChrW(244) & "ng t" & ChrW(225) & "ch)") & vbCrLf & _
            "  - S" & ChrW(7889) & " th" & ChrW(7917) & "a: " & n(2) & IIf(lv(2) > 0, " " & ChrW(8594) & " l" & ChrW(7899) & "p " & lv(2), " (kh" & ChrW(244) & "ng t" & ChrW(225) & "ch)") & vbCrLf & _
            "  - Di" & ChrW(7879) & "n t" & ChrW(237) & "ch: " & n(3) & IIf(lv(3) > 0, " " & ChrW(8594) & " l" & ChrW(7899) & "p " & lv(3), " (kh" & ChrW(244) & "ng t" & ChrW(225) & "ch)") & vbCrLf & _
            "  - Ch" & ChrW(7919) & " kh" & ChrW(225) & "c gi" & ChrW(7919) & " nguy" & ChrW(234) & "n: " & nBo & vbCrLf & vbCrLf & "Th" & ChrW(7921) & "c hi" & ChrW(7879) & "n t" & ChrW(225) & "ch l" & ChrW(7899) & "p?"
        If DC_ThongBao(s, tieuDe, vbYesNo Or vbQuestion) <> vbYes Then Exit Sub
        tong = TL_Chuyen(lv, nDa)
        lst.List(0, 1) = KetQua(nDa)
        DC_ThongBao ChrW(272) & ChrW(227) & " chuy" & ChrW(7875) & "n " & tong & " ch" & ChrW(7919) & ":" & vbCrLf & _
                    "  - Lo" & ChrW(7841) & "i " & ChrW(273) & ChrW(7845) & "t: " & nDa(1) & vbCrLf & _
                    "  - S" & ChrW(7889) & " th" & ChrW(7917) & "a: " & nDa(2) & vbCrLf & _
                    "  - Di" & ChrW(7879) & "n t" & ChrW(237) & "ch: " & nDa(3), tieuDe
        Exit Sub
    End If

    ' ---- nhieu file: hoi 1 lan -> xu ly tung to
    s = "T" & ChrW(225) & "ch l" & ChrW(7899) & "p " & lvN & " cho " & nF & " t" & ChrW(7901) & " b" & ChrW(7843) & "n " & ChrW(273) & ChrW(7891) & IIf(bak, " (c" & ChrW(243) & " sao l" & ChrW(432) & "u .bak)", " (KH" & ChrW(212) & "NG sao l" & ChrW(432) & "u)") & vbCrLf & _
        "  lo" & ChrW(7841) & "i " & ChrW(273) & ChrW(7845) & "t " & ChrW(8594) & " " & IIf(lv(1) > 0, CStr(lv(1)), "kh" & ChrW(244) & "ng t" & ChrW(225) & "ch") & _
        " ; s" & ChrW(7889) & " th" & ChrW(7917) & "a " & ChrW(8594) & " " & IIf(lv(2) > 0, CStr(lv(2)), "kh" & ChrW(244) & "ng t" & ChrW(225) & "ch") & _
        " ; di" & ChrW(7879) & "n t" & ChrW(237) & "ch " & ChrW(8594) & " " & IIf(lv(3) > 0, CStr(lv(3)), "kh" & ChrW(244) & "ng t" & ChrW(225) & "ch") & vbCrLf & vbCrLf & _
        "C" & ChrW(225) & "c file s" & ChrW(7869) & " " & ChrW(273) & ChrW(432) & ChrW(7907) & "c ghi " & ChrW(273) & ChrW(232) & ". Ti" & ChrW(7871) & "p t" & ChrW(7909) & "c?"
    If DC_ThongBao(s, tieuDe, vbYesNo Or vbQuestion) <> vbYes Then Exit Sub

    mDangChay = True
    For i = 0 To nF - 1
        lst.List(i, 1) = ""
    Next i
    For i = 0 To nF - 1
        Me.Controls("lblDem").Caption = " " & (i + 1) & "/" & nF
        Me.Controls("lblPath").Caption = " " & lst.List(i, 0)
        lst.List(i, 1) = ChrW(273) & "ang x" & ChrW(7917) & " l" & ChrW(253) & "..."
        DoEvents
        kq = TL_XuLyFile(CStr(lst.List(i, 0)), lvN, lv, bak, nDa)
        If Len(kq) = 0 Then
            lst.List(i, 1) = KetQua(nDa)
            t1 = t1 + nDa(1): t2 = t2 + nDa(2): t3 = t3 + nDa(3)
            nOK = nOK + 1
        Else
            lst.List(i, 1) = "L" & ChrW(7895) & "i"
            nLoi = nLoi + 1
            If nLoi <= 8 Then Loi = Loi & vbCrLf & "- " & lst.List(i, 0) & ": " & kq
        End If
        DoEvents
    Next i
    mDangChay = False
    On Error Resume Next
    RedrawAllViews
    On Error GoTo 0

    Me.Controls("lblDem").Caption = " " & nF & "/" & nF
    Me.Controls("lblPath").Caption = " Xong: " & nOK & " t" & ChrW(7901) & "."
    s = ChrW(272) & ChrW(227) & " x" & ChrW(7917) & " l" & ChrW(253) & " " & nOK & "/" & nF & " t" & ChrW(7901) & " b" & ChrW(7843) & "n " & ChrW(273) & ChrW(7891) & "." & vbCrLf & _
        "  - Lo" & ChrW(7841) & "i " & ChrW(273) & ChrW(7845) & "t: " & t1 & vbCrLf & "  - S" & ChrW(7889) & " th" & ChrW(7917) & "a: " & t2 & vbCrLf & "  - Di" & ChrW(7879) & "n t" & ChrW(237) & "ch: " & t3
    If nLoi > 0 Then
        s = s & vbCrLf & vbCrLf & "L" & ChrW(7895) & "i " & nLoi & " t" & ChrW(7901) & ":" & Loi
        If nLoi > 8 Then s = s & vbCrLf & "..."
    End If
    DC_ThongBao s, tieuDe, IIf(nLoi > 0, vbExclamation, vbInformation)
End Sub

' SUA 05/11: xoa chu trung (copy/dan 2 lan, cung noi dung chong len nhau)
Private Sub ChayXoaTrung()
    Dim lvN As Long, nF As Long, i As Long, kq As String, bak As Boolean, chiChon As Boolean
    Dim nX As Long, tX As Long, nLoi As Long, Loi As String, s As String, laHT As Boolean, td As String, tol As Double
    td = "X" & ChrW(243) & "a ch" & ChrW(7919) & " tr" & ChrW(249) & "ng"
    nF = lst.ListCount
    If nF = 0 Then
        DC_ThongBao "Danh s" & ChrW(225) & "ch ch" & ChrW(432) & "a c" & ChrW(243) & " t" & ChrW(7901) & " b" & ChrW(7843) & "n " & ChrW(273) & ChrW(7891) & " n" & ChrW(224) & "o.", td, vbExclamation
        Exit Sub
    End If
    lvN = SoLv("cboNguon")
    tol = val(Replace(Trim$(Me.Controls("txtTrung").Text), ",", "."))
    If tol <= 0 Then tol = 0.2
    DC_GhiCauHinh "TLOP_TRUNG", CStr(tol)
    bak = CBool(Me.Controls("chkBak").Value)
    chiChon = CBool(Me.Controls("chkChon").Value)
    On Error Resume Next
    laHT = (StrComp(CStr(lst.List(0, 0)), ActiveDesignFile.FullName, vbTextCompare) = 0)
    On Error GoTo 0
    If Not (nF = 1 And laHT) Then chiChon = False
    s = "X" & ChrW(243) & "a c" & ChrW(225) & "c ch" & ChrW(7919) & " TR" & ChrW(217) & "NG (c" & ChrW(249) & "ng n" & ChrW(7897) & "i dung, c" & ChrW(249) & "ng l" & ChrW(7899) & "p, c" & ChrW(225) & "ch nhau " & ChrW(8804) & " " & tol & " m) " & _
        IIf(lvN > 0, "tr" & ChrW(234) & "n l" & ChrW(7899) & "p " & lvN, "tr" & ChrW(234) & "n M" & ChrW(7884) & "I l" & ChrW(7899) & "p") & _
        IIf(chiChon, " trong c" & ChrW(225) & "c " & ChrW(273) & ChrW(7889) & "i t" & ChrW(432) & ChrW(7907) & "ng " & ChrW(273) & "ang ch" & ChrW(7885) & "n", " trong " & nF & " t" & ChrW(7901) & " b" & ChrW(7843) & "n " & ChrW(273) & ChrW(7891)) & "." & vbCrLf & _
        "M" & ChrW(7895) & "i nh" & ChrW(243) & "m tr" & ChrW(249) & "ng gi" & ChrW(7919) & " l" & ChrW(7841) & "i 1 ch" & ChrW(7919) & "." & vbCrLf & vbCrLf & "Ti" & ChrW(7871) & "p t" & ChrW(7909) & "c?"
    If DC_ThongBao(s, td, vbYesNo Or vbQuestion) <> vbYes Then Exit Sub
    mDangChay = True
    For i = 0 To nF - 1
        Me.Controls("lblDem").Caption = " " & (i + 1) & "/" & nF
        Me.Controls("lblPath").Caption = " " & lst.List(i, 0)
        lst.List(i, 1) = ChrW(273) & "ang x" & ChrW(243) & "a ch" & ChrW(7919) & " tr" & ChrW(249) & "ng..."
        DoEvents
        kq = TL_XoaTrungFile(CStr(lst.List(i, 0)), lvN, bak, chiChon, tol, nX)
        If Len(kq) = 0 Then
            lst.List(i, 1) = "X" & ChrW(243) & "a " & nX & " ch" & ChrW(7919) & " tr" & ChrW(249) & "ng"
            tX = tX + nX
        Else
            lst.List(i, 1) = "L" & ChrW(7895) & "i"
            nLoi = nLoi + 1
            If nLoi <= 8 Then Loi = Loi & vbCrLf & "- " & lst.List(i, 0) & ": " & kq
        End If
        DoEvents
    Next i
    mDangChay = False
    Me.Controls("lblPath").Caption = " Xong x" & ChrW(243) & "a ch" & ChrW(7919) & " tr" & ChrW(249) & "ng: " & tX
    s = ChrW(272) & ChrW(227) & " x" & ChrW(243) & "a " & tX & " ch" & ChrW(7919) & " tr" & ChrW(249) & "ng."
    If nLoi > 0 Then s = s & vbCrLf & vbCrLf & "L" & ChrW(7895) & "i " & nLoi & " t" & ChrW(7901) & ":" & Loi
    DC_ThongBao s, td, IIf(nLoi > 0, vbExclamation, vbInformation)
End Sub

' SUA 25/10: pha chu gop (LUC 766/3860,9 -> LUC | 766 | 3860,9)
Private Sub ChayTachChu()
    Dim lvN As Long, nF As Long, i As Long, kq As String, bak As Boolean, chiChon As Boolean
    Dim nt As Long, tt As Long, nLoi As Long, Loi As String, s As String, laHT As Boolean, td As String
    td = "Ph" & ChrW(225) & " ch" & ChrW(7919) & " g" & ChrW(7897) & "p"
    nF = lst.ListCount
    If nF = 0 Then
        DC_ThongBao "Danh s" & ChrW(225) & "ch ch" & ChrW(432) & "a c" & ChrW(243) & " t" & ChrW(7901) & " b" & ChrW(7843) & "n " & ChrW(273) & ChrW(7891) & " n" & ChrW(224) & "o.", td, vbExclamation
        Exit Sub
    End If
    lvN = SoLv("cboNguon")
    If lvN <= 0 Then
        DC_ThongBao "Ch" & ChrW(432) & "a nh" & ChrW(7853) & "p l" & ChrW(7899) & "p c" & ChrW(7847) & "n t" & ChrW(225) & "ch (l" & ChrW(7899) & "p c" & ChrW(243) & " ch" & ChrW(7919) & " ghi chung).", td, vbExclamation
        Exit Sub
    End If
    bak = CBool(Me.Controls("chkBak").Value)
    chiChon = CBool(Me.Controls("chkChon").Value)
    On Error Resume Next
    laHT = (StrComp(CStr(lst.List(0, 0)), ActiveDesignFile.FullName, vbTextCompare) = 0)
    On Error GoTo 0
    If Not (nF = 1 And laHT) Then chiChon = False
    s = "T" & ChrW(225) & "ch ch" & ChrW(7919) & " ghi chung (vd: LUC 766/3860,9) tr" & ChrW(234) & "n l" & ChrW(7899) & "p " & lvN & IIf(chiChon, " trong c" & ChrW(225) & "c " & ChrW(273) & ChrW(7889) & "i t" & ChrW(432) & ChrW(7907) & "ng " & ChrW(273) & "ang ch" & ChrW(7885) & "n", " trong " & nF & " t" & ChrW(7901) & " b" & ChrW(7843) & "n " & ChrW(273) & ChrW(7891)) & _
        " th" & ChrW(224) & "nh 3 ch" & ChrW(7919) & " ri" & ChrW(234) & "ng: lo" & ChrW(7841) & "i " & ChrW(273) & ChrW(7845) & "t / s" & ChrW(7889) & " th" & ChrW(7917) & "a / di" & ChrW(7879) & "n t" & ChrW(237) & "ch." & vbCrLf & "Sau " & ChrW(273) & ChrW(243) & " b" & ChrW(7845) & "m T" & ChrW(225) & "ch l" & ChrW(7899) & "p." & vbCrLf & vbCrLf & "Ti" & ChrW(7871) & "p t" & ChrW(7909) & "c?"
    If DC_ThongBao(s, td, vbYesNo Or vbQuestion) <> vbYes Then Exit Sub
    mDangChay = True
    For i = 0 To nF - 1
        Me.Controls("lblDem").Caption = " " & (i + 1) & "/" & nF
        Me.Controls("lblPath").Caption = " " & lst.List(i, 0)
        lst.List(i, 1) = ChrW(273) & "ang ph" & ChrW(225) & " ch" & ChrW(7919) & " g" & ChrW(7897) & "p..."
        DoEvents
        kq = TL_TachChuGopFile(CStr(lst.List(i, 0)), lvN, bak, chiChon, nt)
        If Len(kq) = 0 Then
            lst.List(i, 1) = "Ph" & ChrW(225) & " " & nt & " ch" & ChrW(7919) & " g" & ChrW(7897) & "p"
            tt = tt + nt
        Else
            lst.List(i, 1) = "L" & ChrW(7895) & "i"
            nLoi = nLoi + 1
            If nLoi <= 8 Then Loi = Loi & vbCrLf & "- " & lst.List(i, 0) & ": " & kq
        End If
        DoEvents
    Next i
    mDangChay = False
    Me.Controls("lblPath").Caption = " Xong ph" & ChrW(225) & " ch" & ChrW(7919) & " g" & ChrW(7897) & "p: " & tt
    s = ChrW(272) & ChrW(227) & " t" & ChrW(225) & "ch " & tt & " ch" & ChrW(7919) & " ghi chung th" & ChrW(224) & "nh ch" & ChrW(7919) & " ri" & ChrW(234) & "ng. Gi" & ChrW(7901) & " b" & ChrW(7845) & "m T" & ChrW(225) & "ch l" & ChrW(7899) & "p."
    If nLoi > 0 Then s = s & vbCrLf & vbCrLf & "L" & ChrW(7895) & "i " & nLoi & " t" & ChrW(7901) & ":" & Loi
    DC_ThongBao s, td, IIf(nLoi > 0, vbExclamation, vbInformation)
End Sub

Private Sub ChayPhaKhoi()
    Dim lvN As Long, nF As Long, i As Long, kq As String, bak As Boolean, chiChon As Boolean
    Dim nPha As Long, nSh As Long, tPha As Long, tSh As Long, nLoi As Long, Loi As String, s As String, laHT As Boolean
    nF = lst.ListCount
    If nF = 0 Then
        DC_ThongBao "Danh s" & ChrW(225) & "ch ch" & ChrW(432) & "a c" & ChrW(243) & " t" & ChrW(7901) & " b" & ChrW(7843) & "n " & ChrW(273) & ChrW(7891) & " n" & ChrW(224) & "o.", "Ph" & ChrW(225) & " kh" & ChrW(7889) & "i", vbExclamation
        Exit Sub
    End If
    lvN = SoLv("cboNguon")
    bak = CBool(Me.Controls("chkBak").Value)
    chiChon = CBool(Me.Controls("chkChon").Value)
    On Error Resume Next
    laHT = (StrComp(CStr(lst.List(0, 0)), ActiveDesignFile.FullName, vbTextCompare) = 0)
    On Error GoTo 0
    If Not (nF = 1 And laHT) Then chiChon = False
    s = "Ph" & ChrW(225) & " c" & ChrW(225) & "c kh" & ChrW(7889) & "i (cell) c" & ChrW(243) & " ch" & ChrW(7919) & " " & IIf(lvN > 0, "tr" & ChrW(234) & "n l" & ChrW(7899) & "p " & lvN, "(m" & ChrW(7885) & "i l" & ChrW(7899) & "p)") & _
        IIf(chiChon, " trong c" & ChrW(225) & "c " & ChrW(273) & ChrW(7889) & "i t" & ChrW(432) & ChrW(7907) & "ng " & ChrW(273) & "ang ch" & ChrW(7885) & "n", " trong " & nF & " t" & ChrW(7901) & " b" & ChrW(7843) & "n " & ChrW(273) & ChrW(7891)) & " th" & ChrW(224) & "nh ch" & ChrW(7919) & " / n" & ChrW(233) & "t r" & ChrW(7901) & "i." & vbCrLf & _
        IIf(bak And Not (nF = 1 And laHT), "(C" & ChrW(243) & " sao l" & ChrW(432) & "u .bak)", "(File " & ChrW(273) & "ang m" & ChrW(7903) & ": kh" & ChrW(244) & "ng ho" & ChrW(224) & "n t" & ChrW(225) & "c b" & ChrW(7857) & "ng undo mark " & ChrW(273) & ChrW(432) & ChrW(7907) & "c)") & vbCrLf & vbCrLf & "Ti" & ChrW(7871) & "p t" & ChrW(7909) & "c?"
    If DC_ThongBao(s, "Ph" & ChrW(225) & " kh" & ChrW(7889) & "i", vbYesNo Or vbQuestion) <> vbYes Then Exit Sub

    mDangChay = True
    For i = 0 To nF - 1
        Me.Controls("lblDem").Caption = " " & (i + 1) & "/" & nF
        Me.Controls("lblPath").Caption = " " & lst.List(i, 0)
        lst.List(i, 1) = ChrW(273) & "ang ph" & ChrW(225) & " kh" & ChrW(7889) & "i..."
        DoEvents
        kq = TL_PhaKhoiFile(CStr(lst.List(i, 0)), lvN, bak, chiChon, nPha, nSh)
        If Len(kq) = 0 Then
            lst.List(i, 1) = "Ph" & ChrW(225) & " " & nPha & " kh" & ChrW(7889) & "i" & IIf(nSh > 0, " (" & nSh & " shared)", "")
            tPha = tPha + nPha: tSh = tSh + nSh
        Else
            lst.List(i, 1) = "L" & ChrW(7895) & "i"
            nLoi = nLoi + 1
            If nLoi <= 8 Then Loi = Loi & vbCrLf & "- " & lst.List(i, 0) & ": " & kq
        End If
        DoEvents
    Next i
    mDangChay = False
    Me.Controls("lblPath").Caption = " Xong ph" & ChrW(225) & " kh" & ChrW(7889) & "i: " & tPha & " kh" & ChrW(7889) & "i."
    s = ChrW(272) & ChrW(227) & " ph" & ChrW(225) & " " & tPha & " kh" & ChrW(7889) & "i c" & ChrW(243) & " ch" & ChrW(7919) & ". Gi" & ChrW(7901) & " b" & ChrW(7845) & "m T" & ChrW(225) & "ch l" & ChrW(7899) & "p."
    If tSh > 0 Then s = s & vbCrLf & vbCrLf & "C" & ChrW(243) & " " & tSh & " kh" & ChrW(7889) & "i d" & ChrW(249) & "ng chung (shared cell) ch" & ChrW(432) & "a ph" & ChrW(225) & " " & ChrW(273) & ChrW(432) & ChrW(7907) & "c b" & ChrW(7857) & "ng c" & ChrW(244) & "ng c" & ChrW(7909) & " n" & ChrW(224) & "y - d" & ChrW(249) & "ng Drop Element c" & ChrW(7911) & "a MicroStation (tick Shared Cells)."
    If nLoi > 0 Then s = s & vbCrLf & vbCrLf & "L" & ChrW(7895) & "i " & nLoi & " t" & ChrW(7901) & ":" & Loi
    DC_ThongBao s, "Ph" & ChrW(225) & " kh" & ChrW(7889) & "i", IIf(nLoi > 0, vbExclamation, vbInformation)
End Sub

Private Function KetQua(ByRef nDa() As Long) As String
    KetQua = "L" & ChrW(272) & " " & nDa(1) & " / ST " & nDa(2) & " / DT " & nDa(3)
End Function

Private Sub UserForm_Terminate()
    DC_CuonTat
End Sub

Attribute VB_Name = "frmTaoThua"
Attribute VB_Base = "0{D61BC85C-FCFF-431D-BA89-5E202ECDA4C7}{3A885640-E359-486B-B72C-C7C415015680}"
Attribute VB_GlobalNameSpace = False
Attribute VB_Creatable = False
Attribute VB_PredeclaredId = True
Attribute VB_Exposed = False
Attribute VB_TemplateDerived = False
Attribute VB_Customizable = False
'============================================================
' frmTaoThua - Tao Topology / CSDL (Viet hoa ChrW, Arial)
'   Co nut Xoa nhan. Tieu de thanh de ASCII (font he thong).
'============================================================
Option Explicit
' SUA 28/10: lan con chuot cuon ListBox (modCuonChuot)
Private mCuon0 As Object

Private mNut As New Collection

Private Sub UserForm_Initialize()
    Me.Caption = "Tao Topology / CSDL"
    Me.Font.Name = "Arial"
    Me.Font.size = 8
    Me.Width = 320
    Me.Height = 400

    ' Danh sach level (tick chon)
    AddLabel "lblLv", "L" & ChrW(7899) & "p ranh (tick):", 8, 6, 130
    Dim lst As Object
    Set lst = Me.Controls.Add("Forms.ListBox.1", "lstLevel", True)
    Set mCuon0 = DC_GanCuon(lst, Me)     ' SUA 28/10: lan chuot cuon danh sach
    lst.Left = 8: lst.Top = 20: lst.Width = 120: lst.Height = 250
    lst.ListStyle = 1: lst.MultiSelect = 1
    lst.Font.Name = "Arial": lst.Font.size = 8
    Dim i As Long
    For i = 1 To 63
        lst.AddItem "Level " & i
    Next i

    Dim x As Single: x = 140
    AddPair "Lo" & ChrW(7841) & "i " & ChrW(273) & ChrW(7845) & "t:", "txtLoaiDat", "", x, 20
    AddPair "T" & ChrW(7901) & " b" & ChrW(7843) & "n " & ChrW(273) & ChrW(7891) & ":", "txtToBanDo", "", x, 44
    AddPair "S" & ChrW(7889) & " l" & ChrW(7867) & " DT:", "txtSoLe", "1", x, 68
    AddPair "B" & ChrW(7887) & " v" & ChrW(249) & "ng <(m" & ChrW(178) & "):", "txtBoNho", "0", x, 92
    AddPair "Snap:", "txtSnap", "0.05", x, 116
    AddPair "L" & ChrW(7899) & "p t" & ChrW(226) & "m:", "txtLevelTam", "Level 11", x, 140
    AddPair "M" & ChrW(224) & "u t" & ChrW(226) & "m:", "txtMau", "5", x, 164
    AddPair "KT t" & ChrW(226) & "m (m):", "txtKT", "0.3", x, 188
    AddPair "File CSDL:", "txtCSDL", "", x, 212
    AddPair "M" & ChrW(224) & "u ranh (tr" & ChrW(7889) & "ng=h" & ChrW(7871) & "t):", "txtMauRanh", "", x, 236
    AddPair "B" & ChrW(7855) & "t h" & ChrW(7903) & " (m):", "txtBatHo", "0", x, 260

    ' Mac dinh CSDL theo ten file .dgn dang mo
    Me.Controls("txtCSDL").Text = CsdlMacDinh()
    ' SUA 23/10: to ban do tu ten file dgn (DC9 -> 9)
    Me.Controls("txtToBanDo").Text = DC_ToTheoTenFile()

    Dim b1 As Object, b2 As Object, b3 As Object
    Set b1 = Me.Controls.Add("Forms.CommandButton.1", "cmdOK", True)
    b1.Caption = "Ch" & ChrW(7845) & "p nh" & ChrW(7853) & "n": b1.Left = 140: b1.Top = 300: b1.Width = 80: b1.Height = 24
    b1.Font.Name = "Arial": b1.Font.size = 8
    Set b2 = Me.Controls.Add("Forms.CommandButton.1", "cmdDong", True)
    b2.Caption = ChrW(272) & ChrW(243) & "ng": b2.Left = 226: b2.Top = 300: b2.Width = 70: b2.Height = 24
    b2.Font.Name = "Arial": b2.Font.size = 8
    Set b3 = Me.Controls.Add("Forms.CommandButton.1", "cmdXoaNhan", True)
    b3.Caption = "X" & ChrW(243) & "a nh" & ChrW(227) & "n": b3.Left = 8: b3.Top = 332: b3.Width = 120: b3.Height = 24
    b3.Font.Name = "Arial": b3.Font.size = 8

    ' SUA 11/10/2026: chia doan tai giao diem tren ban ve truoc khi tao vung
    Dim ckC As Object
    Set ckC = Me.Controls.Add("Forms.CheckBox.1", "chkChiaDoan", True)
    ckC.Caption = "Chia " & ChrW(273) & "o" & ChrW(7841) & "n t" & ChrW(7841) & "i giao " & ChrW(273) & "i" & ChrW(7875) & "m (c" & ChrW(7855) & "t n" & ChrW(233) & "t ranh) + x" & ChrW(243) & "a " & ChrW(273) & "o" & ChrW(7841) & "n d" & ChrW(432) & " < 0,5 m"
    ckC.Left = 8: ckC.Top = 280: ckC.Width = 300: ckC.Height = 16
    ckC.Font.Name = "Arial": ckC.Font.size = 8
    ckC.Value = (DC_DocCauHinh("CHIA_TOPO", "1") = "1")

    Dim ck As Object
    Set ck = Me.Controls.Add("Forms.CheckBox.1", "chkTheoDiem", True)
    ck.Caption = "T" & ChrW(7841) & "o theo " & ChrW(273) & "i" & ChrW(7875) & "m b" & ChrW(7845) & "m"
    ck.Left = 8: ck.Top = 300: ck.Width = 128: ck.Height = 16
    ck.Font.Name = "Arial": ck.Font.size = 8

    Dim h1 As clsNutTL, h2 As clsNutTL, h3 As clsNutTL
    Set h1 = New clsNutTL: Set h1.btn = b1: Set h1.Form = Me: h1.ma = "OK": mNut.Add h1
    Set h2 = New clsNutTL: Set h2.btn = b2: Set h2.Form = Me: h2.ma = "DONG": mNut.Add h2
    Set h3 = New clsNutTL: Set h3.btn = b3: Set h3.Form = Me: h3.ma = "XOANHAN": mNut.Add h3
End Sub

Private Sub AddLabel(ByVal nm As String, ByVal cap As String, _
                     ByVal x As Single, ByVal y As Single, ByVal w As Single)
    Dim c As Object
    Set c = Me.Controls.Add("Forms.Label.1", nm, True)
    c.Caption = cap: c.Left = x: c.Top = y: c.Width = w: c.Height = 12
    c.Font.Name = "Arial": c.Font.size = 8
End Sub

Private Sub AddPair(ByVal cap As String, ByVal nm As String, ByVal txt As String, _
                    ByVal x As Single, ByVal y As Single)
    AddLabel "lbl_" & nm, cap, x, y + 2, 70
    Dim c As Object
    Set c = Me.Controls.Add("Forms.TextBox.1", nm, True)
    c.Text = txt: c.Left = x + 72: c.Top = y: c.Width = 96: c.Height = 15
    c.Font.Name = "Arial": c.Font.size = 8
End Sub

Public Sub XuLyNut(ByVal ma As String)
    If ma = "DONG" Then Unload Me: Exit Sub
    If ma = "XOANHAN" Then
        Me.Hide
        DC_XoaNhanTheoLevel
        Me.Show vbModeless
        Exit Sub
    End If

    ' ma = "OK"
    Dim lst As Object, csv As String, i As Long
    Set lst = Me.Controls("lstLevel")
    For i = 0 To lst.ListCount - 1
        If lst.Selected(i) Then
            If Len(csv) > 0 Then csv = csv & ","
            csv = csv & lst.List(i)
        End If
    Next i
    If Len(csv) = 0 Then MsgBox "Ch" & ChrW(432) & "a ch" & ChrW(7885) & "n level ranh.", vbExclamation: Exit Sub

    ' Chia doan tai giao diem (sua that net ranh tren ban ve)
    DC_GhiCauHinh "CHIA_TOPO", IIf(Me.Controls("chkChiaDoan").Value, "1", "0")
    If Me.Controls("chkChiaDoan").Value Then
        Dim sn As Double
        sn = val(Me.Controls("txtSnap").Text): If sn <= 0 Then sn = 0.05
        DC_ChiaDoanGiao csv, sn, val(DC_DocCauHinh("CHIA_DU", "0.5")), False
    End If

    ' Che do TAO THEO DIEM BAM -> giao cho cong cu bat diem, an form
    If Me.Controls("chkTheoDiem").Value Then
        Me.Hide
        DC_TaoVungTheoDiem csv, Me.Controls("txtLoaiDat").Text, Me.Controls("txtToBanDo").Text, _
                val(Me.Controls("txtSnap").Text), Me.Controls("txtLevelTam").Text, _
                CLng(val(Me.Controls("txtMau").Text)), val(Me.Controls("txtKT").Text), _
                Me.Controls("txtCSDL").Text, Me.Controls("txtMauRanh").Text, _
                val(Me.Controls("txtBatHo").Text)
        Exit Sub
    End If

    Me.Hide
    ChayTaoThua csv, Me.Controls("txtLoaiDat").Text, Me.Controls("txtToBanDo").Text, _
                CLng(val(Me.Controls("txtSoLe").Text)), val(Me.Controls("txtBoNho").Text), _
                val(Me.Controls("txtSnap").Text), Me.Controls("txtLevelTam").Text, _
                CLng(val(Me.Controls("txtMau").Text)), val(Me.Controls("txtKT").Text), _
                Me.Controls("txtCSDL").Text, Me.Controls("txtMauRanh").Text, _
                val(Me.Controls("txtBatHo").Text)
    Me.Show vbModeless
End Sub

Private Sub UserForm_Terminate()
    DC_CuonTat
End Sub

Attribute VB_Name = "frmTimLoi2"
Attribute VB_Base = "0{1AC69D10-7740-4CCC-B0C7-4C17556C9A33}{0A63B514-252C-4D0A-9C2B-AB011B4D044A}"
Attribute VB_GlobalNameSpace = False
Attribute VB_Creatable = False
Attribute VB_PredeclaredId = True
Attribute VB_Exposed = False
Attribute VB_TemplateDerived = False
Attribute VB_Customizable = False
'============================================================
' frmTimLoi2 - Tim loi du lieu (Viet hoa ChrW, Arial)
'   Tieu de thanh de ASCII (font he thong).
'============================================================
Option Explicit
' SUA 28/10: lan con chuot cuon ListBox (modCuonChuot)
Private mCuon0 As Object

Private mNut As New Collection

Private Sub UserForm_Initialize()
    Me.Caption = "Tim loi du lieu"
    Me.Font.Name = "Arial"
    Me.Font.size = 8
    Me.Width = 312
    Me.Height = 420

    ' Danh sach level (tick chon)
    AddLabel "lblLv", "L" & ChrW(7899) & "p c" & ChrW(7841) & "nh (tick ch" & ChrW(7885) & "n):", 8, 6, 160
    Dim lst As Object
    Set lst = Me.Controls.Add("Forms.ListBox.1", "lstLevel", True)
    Set mCuon0 = DC_GanCuon(lst, Me)     ' SUA 28/10: lan chuot cuon danh sach
    lst.Left = 8: lst.Top = 22: lst.Width = 150: lst.Height = 300
    lst.ListStyle = 1
    lst.MultiSelect = 1
    lst.Font.Name = "Arial": lst.Font.size = 8
    Dim i As Long
    For i = 1 To 63
        lst.AddItem "Level " & i
    Next i

    ' Loai loi
    Dim x As Single: x = 175
    AddLabel "lblLoai", "Lo" & ChrW(7841) & "i l" & ChrW(7895) & "i c" & ChrW(7847) & "n " & ChrW(273) & ChrW(225) & "nh d" & ChrW(7845) & "u:", x, 6, 130
    AddCheck "chkD", "(D) " & ChrW(272) & ChrW(7881) & "nh treo / h" & ChrW(7903) & " ranh", x, 24, True
    AddCheck "chkS", "(S) C" & ChrW(7841) & "nh ng" & ChrW(7855) & "n", x, 44, False
    AddCheck "chkA", "(A) Th" & ChrW(7917) & "a nh" & ChrW(7887), x, 64, False
    AddCheck "chkX", "(X) Giao " & ChrW(273) & "i" & ChrW(7875) & "m", x, 84, False
    AddCheck "chkO", "(O) Ch" & ChrW(7891) & "ng " & ChrW(273) & ChrW(232), x, 104, False
    AddCheck "chkE", "(E) C" & ChrW(7841) & "nh sai", x, 124, False

    ' Nguong
    AddLabel "lblCN", "Gi" & ChrW(7899) & "i h" & ChrW(7841) & "n c" & ChrW(7841) & "nh ng" & ChrW(7855) & "n (m):", x, 152, 130
    AddText "txtCanhNgan", "0.05", x, 168
    AddLabel "lblTN", "Gi" & ChrW(7899) & "i h" & ChrW(7841) & "n th" & ChrW(7917) & "a nh" & ChrW(7887) & " (m" & ChrW(178) & "):", x, 192, 130
    AddText "txtThuaNho", "0.3", x, 208
    AddLabel "lblSnap", ChrW(272) & ChrW(7897) & " ch" & ChrW(237) & "nh x" & ChrW(225) & "c (snap):", x, 232, 130
    AddText "txtSnap", "0.05", x, 248
    AddLabel "lblLoi", "L" & ChrW(7899) & "p th" & ChrW(244) & "ng b" & ChrW(225) & "o l" & ChrW(7895) & "i:", x, 272, 130
    AddText "txtLevelLoi", "Level 40", x, 288

    AddLabel "lblMau", "M" & ChrW(224) & "u ranh (tr" & ChrW(7889) & "ng=h" & ChrW(7871) & "t):", x, 312, 130
    AddText "txtMauRanh", "", x, 328

    ' Hai nut
    Dim b1 As Object, b2 As Object
    Set b1 = Me.Controls.Add("Forms.CommandButton.1", "cmdOK", True)
    b1.Caption = "Ch" & ChrW(7845) & "p nh" & ChrW(7853) & "n": b1.Left = 175: b1.Top = 360: b1.Width = 62: b1.Height = 28
    b1.Font.Name = "Arial": b1.Font.size = 8
    Set b2 = Me.Controls.Add("Forms.CommandButton.1", "cmdDong", True)
    b2.Caption = ChrW(272) & ChrW(243) & "ng": b2.Left = 241: b2.Top = 360: b2.Width = 58: b2.Height = 28
    b2.Font.Name = "Arial": b2.Font.size = 8

    Dim h1 As clsNutTL, h2 As clsNutTL
    Set h1 = New clsNutTL: Set h1.btn = b1: Set h1.Form = Me: h1.ma = "OK": mNut.Add h1
    Set h2 = New clsNutTL: Set h2.btn = b2: Set h2.Form = Me: h2.ma = "DONG": mNut.Add h2
End Sub

Private Sub AddLabel(ByVal nm As String, ByVal cap As String, _
                     ByVal x As Single, ByVal y As Single, ByVal w As Single)
    Dim c As Object
    Set c = Me.Controls.Add("Forms.Label.1", nm, True)
    c.Caption = cap: c.Left = x: c.Top = y: c.Width = w: c.Height = 14
    c.Font.Name = "Arial": c.Font.size = 8
End Sub

Private Sub AddCheck(ByVal nm As String, ByVal cap As String, _
                     ByVal x As Single, ByVal y As Single, ByVal v As Boolean)
    Dim c As Object
    Set c = Me.Controls.Add("Forms.CheckBox.1", nm, True)
    c.Caption = cap: c.Left = x: c.Top = y: c.Width = 130: c.Height = 16
    c.Value = v
    c.Font.Name = "Arial": c.Font.size = 8
End Sub

Private Sub AddText(ByVal nm As String, ByVal txt As String, _
                    ByVal x As Single, ByVal y As Single)
    Dim c As Object
    Set c = Me.Controls.Add("Forms.TextBox.1", nm, True)
    c.Text = txt: c.Left = x: c.Top = y: c.Width = 95: c.Height = 16
    c.Font.Name = "Arial": c.Font.size = 8
End Sub

Public Sub XuLyNut(ByVal ma As String)
    If ma = "DONG" Then
        Unload Me
        Exit Sub
    End If

    Dim lst As Object, csv As String, i As Long
    Set lst = Me.Controls("lstLevel")
    For i = 0 To lst.ListCount - 1
        If lst.Selected(i) Then
            If Len(csv) > 0 Then csv = csv & ","
            csv = csv & lst.List(i)
        End If
    Next i
    If Len(csv) = 0 Then
        MsgBox "Ch" & ChrW(432) & "a ch" & ChrW(7885) & "n level c" & ChrW(7841) & "nh n" & ChrW(224) & "o.", vbExclamation, "Tim loi"
        Exit Sub
    End If

    Dim canhNgan As Double, thuaNho As Double, snap As Double
    canhNgan = val(Me.Controls("txtCanhNgan").Text)
    thuaNho = val(Me.Controls("txtThuaNho").Text)
    snap = val(Me.Controls("txtSnap").Text)

    Me.Hide
    ChayTimLoi csv, _
               Me.Controls("chkD").Value, Me.Controls("chkS").Value, _
               Me.Controls("chkA").Value, Me.Controls("chkX").Value, _
               Me.Controls("chkO").Value, Me.Controls("chkE").Value, _
               canhNgan, thuaNho, snap, Me.Controls("txtLevelLoi").Text, _
               Me.Controls("txtMauRanh").Text
    Me.Show vbModeless
End Sub

Private Sub UserForm_Terminate()
    DC_CuonTat
End Sub

Attribute VB_Name = "frmTrichLuc"
Attribute VB_Base = "0{D3DB3021-55D2-4FA6-9951-A1214E46DA95}{C70A3ADF-9CDC-40FD-BBFB-B334BACB77C8}"
Attribute VB_GlobalNameSpace = False
Attribute VB_Creatable = False
Attribute VB_PredeclaredId = True
Attribute VB_Exposed = False
Attribute VB_TemplateDerived = False
Attribute VB_Customizable = False
'============================================================
' frmTrichLuc - Trich luc thua dat (Viet hoa, chu nho Arial 8)
'   Them combo "Ty le ban do" -> khoi bi hoi popup moi lan Chap nhan.
'   Can clsNutTL, clsComboEvent, modMaXa.
'============================================================
Option Explicit

Private Const MAXA_PATH As String = "C:\DiaChinhVL\MaXaVN.txt"

Private mNut As New Collection
Private mCbo As clsComboEvent
Private mCboHS As clsComboEvent
Private mLoai As Long          ' 0 = trich luc, 1 = tach thua, 2 = hop thua

Private Sub UserForm_Initialize()
    ChuyenMauTT26          ' SUA 22/10: 1 lan / may - dat 4 mau TT26 mac dinh
    Me.Caption = "Trich luc thua dat"   ' title bar de ASCII (font he thong)
    Me.Font.Name = "Arial"
    Me.Font.size = 8
    Me.Width = 322
    Me.Height = 462

    Dim TINH_MD As String
    TINH_MD = "T" & ChrW(7881) & "nh V" & ChrW(297) & "nh Long"   ' Tinh Vinh Long

    Dim x As Single: x = 10
    AddPairW "File CSDL:", "txtCSDL", "", x, 8, 190
    ' Mau ho so + file mau (.dgn kieu gCadas hoac .txt) + file cau hinh .ini
    AddLbl "lbl_mauhs", "M" & ChrW(7851) & "u h" & ChrW(7891) & " s" & ChrW(417) & ":", x, 34, 100
    Dim cM As Object
    Set cM = Me.Controls.Add("Forms.ComboBox.1", "cboMauHS", True)
    cM.Left = x + 104: cM.Top = 32: cM.Width = 190: cM.Height = 18
    cM.Font.Name = "Arial": cM.Font.size = 8: cM.Style = 2
    cM.AddItem "Tr" & ChrW(237) & "ch l" & ChrW(7909) & "c b" & ChrW(7843) & "n " & ChrW(273) & ChrW(7891) & " " & ChrW(273) & ChrW(7883) & "a ch" & ChrW(237) & "nh (TT26)"
    cM.AddItem "T" & ChrW(225) & "ch th" & ChrW(7917) & "a " & ChrW(273) & ChrW(7845) & "t (TT26 - m" & ChrW(7851) & "u 22/" & ChrW(272) & "K)"
    cM.AddItem "H" & ChrW(7907) & "p th" & ChrW(7917) & "a " & ChrW(273) & ChrW(7845) & "t (TT26 - m" & ChrW(7851) & "u 22/" & ChrW(272) & "K)"
    cM.AddItem "Phi" & ChrW(7871) & "u " & ChrW(273) & "o " & ChrW(273) & ChrW(7841) & "c ch" & ChrW(7881) & "nh l" & ChrW(253) & " (TT26)"
    cM.ListIndex = 0
    AddPairW "File m" & ChrW(7851) & "u:", "txtMau", DC_DocCauHinh("MAU_TL", "C:\DiaChinhVL\TrichLucBanDo_mau.txt"), x, 56, 164
    AddPairW "File c" & ChrW(7845) & "u h" & ChrW(236) & "nh:", "txtIni", DC_DocCauHinh("INI_TL", ""), x, 80, 164
    ThemNutNho "CHONMAU", "...", x + 272, 56
    ThemNutNho "CHONINI", "...", x + 272, 80
    AddPair "S" & ChrW(7889) & " th" & ChrW(7917) & "a tr" & ChrW(237) & "ch l" & ChrW(7909) & "c:", "txtSoThua", "", x, 104
    AddPair "T" & ChrW(7901) & " b" & ChrW(7843) & "n " & ChrW(273) & ChrW(7891) & ":", "txtTo", "", x, 128
    ' Level duong cat (chi dung khi tach thua)
    AddLbl "lbl_lvcat", "Lv c" & ChrW(7855) & "t:", x + 230, 130, 30
    Dim tC As Object
    Set tC = Me.Controls.Add("Forms.TextBox.1", "txtLvCat", True)
    tC.Text = DC_DocCauHinh("TACH_LV", "18"): tC.Left = x + 262: tC.Top = 128: tC.Width = 32: tC.Height = 16
    tC.Font.Name = "Arial": tC.Font.size = 8

    ' Nut chon thua tren ban do -> xuat trich luc thua do (khong can go so thua)
    Dim bC As Object, hc As clsNutTL
    Set bC = Me.Controls.Add("Forms.CommandButton.1", "cmdChon", True)
    bC.Caption = "Ch" & ChrW(7885) & "n th" & ChrW(7917) & "a"
    bC.Left = x + 230: bC.Top = 102: bC.Width = 64: bC.Height = 20
    bC.Font.Name = "Arial": bC.Font.size = 8: bC.Font.Bold = True
    Set hc = New clsNutTL: Set hc.btn = bC: Set hc.Form = Me: hc.ma = "CHON": mNut.Add hc

    ' Tinh (combo) + Xa (combo)
    AddLbl "lbl_tinh", "T" & ChrW(7881) & "nh:", x, 154, 100
    Dim cboT As Object
    Set cboT = Me.Controls.Add("Forms.ComboBox.1", "cboTinh", True)
    cboT.Left = x + 104: cboT.Top = 152: cboT.Width = 190: cboT.Height = 18
    cboT.Font.Name = "Arial": cboT.Font.size = 8

    AddLbl "lbl_xa", "X" & ChrW(227) & " / ph" & ChrW(432) & ChrW(7901) & "ng:", x, 178, 100
    Dim cboX As Object
    Set cboX = Me.Controls.Add("Forms.ComboBox.1", "cboXa", True)
    cboX.Left = x + 104: cboX.Top = 176: cboX.Width = 190: cboX.Height = 18
    cboX.Font.Name = "Arial": cboX.Font.size = 8

    AddPair "Huy" & ChrW(7879) & "n (n" & ChrW(7871) & "u c" & ChrW(243) & "):", "txtHuyen", "", x, 202
    ' Level ho so / Level so do (giong gCadas). 1 so = ve het vao level do;
    ' nhieu so = level ho so giu level file mau, level so do: canh/so dinh/nhan
    ThemDongLevel "chkLvHS", "Level h" & ChrW(7891) & " s" & ChrW(417), "txtLvHS", DC_DocCauHinh("LV_HS", DC_LV_HS_MD), _
                  DC_DocCauHinh("LV_HS_ON", "1") = "1", "XOAHS", x, 226
    ThemDongLevel "chkLvSD", "Level s" & ChrW(417) & " " & ChrW(273) & ChrW(7891), "txtLvSD", DC_DocCauHinh("LV_SD", DC_LV_SD_MD), _
                  DC_DocCauHinh("LV_SD_ON", "1") = "1", "XOASD", x, 250
    AddPair "C" & ChrW(7905) & " ch" & ChrW(7919) & " (t" & ChrW(7921) & " v" & ChrW(7869) & "):", "txtCao", "1", x, 276
    AddPair "Ki" & ChrW(7875) & "u c" & ChrW(259) & "n (T/G):", "txtKieu", "T", x, 300
    ' SUA 16/10/2026: an Co chu / Kieu can (dung mac dinh 1 / T), nhuong cho ty le 2 dong
    Me.Controls("txtCao").Visible = False: Me.Controls("lbl_txtCao").Visible = False
    Me.Controls("txtKieu").Visible = False: Me.Controls("lbl_txtKieu").Visible = False
    Me.Controls("txtCao").Text = "1": Me.Controls("txtKieu").Text = "T"

    ' Ty le ban do (combo) - thay cho InputBox moi lan chen khung
    AddLbl "lbl_tyle", "T" & ChrW(7927) & " l" & ChrW(7879) & " b" & ChrW(7843) & "n " & ChrW(273) & ChrW(7891) & ":", x, 280, 100
    Dim cboTL As Object
    Set cboTL = Me.Controls.Add("Forms.ComboBox.1", "cboTyLe", True)
    cboTL.Left = x + 104: cboTL.Top = 278: cboTL.Width = 90: cboTL.Height = 18
    cboTL.Font.Name = "Arial": cboTL.Font.size = 8
    cboTL.AddItem "T" & ChrW(7921) & " " & ChrW(273) & ChrW(7897) & "ng"
    cboTL.AddItem "200"
    cboTL.AddItem "500"
    cboTL.AddItem "700"
    cboTL.AddItem "1000"
    cboTL.AddItem "2000"
    cboTL.AddItem "5000"
    cboTL.AddItem "10000"
    cboTL.ListIndex = 0          ' mac dinh: Tu dong (theo kich thuoc thua)
    ' SUA 16/10/2026: nho ty le lan truoc; go tay ty le bat ky (vd 700, 2500)
    Dim tlCu As String
    tlCu = DC_DocCauHinh("TL_TYLE", "")
    If val(tlCu) > 0 Then cboTL.Value = tlCu
    ' SUA 16/10/2026 (2): o "1:" go ty le tuy y (vd 700, 2500). Co so -> dung so nay
    ' (ca trich luc lan tach/hop thua); de trong -> theo o chon ben trai.
    AddLbl "lbl_tyletay", "T" & ChrW(7927) & " l" & ChrW(7879) & " t" & ChrW(249) & "y " & ChrW(253) & ":      1 :", x, 306, 100
    Dim tt As Object
    Set tt = Me.Controls.Add("Forms.TextBox.1", "txtTyLeTay", True)
    tt.Left = x + 104: tt.Top = 304: tt.Width = 90: tt.Height = 18
    tt.Font.Name = "Arial": tt.Font.size = 8
    tt.ControlTipText = "Go ty le tuy y (vd 700, 2500). De trong = theo o chon"
    tt.Text = DC_DocCauHinh("TL_TYLE_TAY", "")
    ' ghi chu mo (xam, chu nho) duoi o ty le
    Dim gc As Object
    Set gc = Me.Controls.Add("Forms.Label.1", "lbl_tylegc", True)
    gc.Caption = "G" & ChrW(245) & " s" & ChrW(7889) & " (vd 700, 2500) th" & ChrW(236) & " d" & ChrW(249) & "ng s" & ChrW(7889) & " n" & ChrW(224) & "y; " & ChrW(273) & ChrW(7875) & " tr" & ChrW(7889) & "ng = theo " & ChrW(244) & " T" & ChrW(7927) & " l" & ChrW(7879) & " b" & ChrW(7843) & "n " & ChrW(273) & ChrW(7891)
    gc.Left = x + 104: gc.Top = 324: gc.Width = 200: gc.Height = 22: gc.WordWrap = True
    gc.Font.Name = "Arial": gc.Font.size = 7: gc.ForeColor = &H808080

    Dim c As Object
    Set c = Me.Controls.Add("Forms.CheckBox.1", "chkMau", True)
    c.Caption = "Ch" & ChrW(232) & "n khung Ph" & ChrW(7909) & " l" & ChrW(7909) & "c 19 (b" & ChrW(7887) & " tick = s" & ChrW(417) & " " & ChrW(273) & ChrW(7891) & " t" & ChrW(7921) & " v" & ChrW(7869) & ")"
    c.Left = x: c.Top = 355: c.Width = 290: c.Height = 16: c.Value = True
    c.Font.Name = "Arial": c.Font.size = 8

    Dim b1 As Object, b2 As Object
    Set b1 = Me.Controls.Add("Forms.CommandButton.1", "cmdOK", True)
    b1.Caption = "Ch" & ChrW(7845) & "p nh" & ChrW(7853) & "n": b1.Left = 124: b1.Top = 402: b1.Width = 88: b1.Height = 24
    b1.Font.Name = "Arial": b1.Font.size = 8
    Set b2 = Me.Controls.Add("Forms.CommandButton.1", "cmdDong", True)
    b2.Caption = ChrW(272) & ChrW(243) & "ng": b2.Left = 216: b2.Top = 402: b2.Width = 88: b2.Height = 24
    b2.Font.Name = "Arial": b2.Font.size = 8
    Dim h1 As clsNutTL, h2 As clsNutTL
    Set h1 = New clsNutTL: Set h1.btn = b1: Set h1.Form = Me: h1.ma = "OK": mNut.Add h1
    Set h2 = New clsNutTL: Set h2.btn = b2: Set h2.Form = Me: h2.ma = "DONG": mNut.Add h2
    ' Luu file ho so: trich luc vua xuat -> file .dgn rieng
    Dim b3 As Object, h3 As clsNutTL
    Set b3 = Me.Controls.Add("Forms.CommandButton.1", "cmdLuuHS", True)
    b3.Caption = "L" & ChrW(432) & "u file h" & ChrW(7891) & " s" & ChrW(417): b3.Left = x: b3.Top = 402: b3.Width = 110: b3.Height = 24
    b3.Font.Name = "Arial": b3.Font.size = 8
    Set h3 = New clsNutTL: Set h3.btn = b3: Set h3.Form = Me: h3.ma = "LUUHS": mNut.Add h3
    ' Tat / bat lop ban do (chi chua lop trich luc)
    ThemNutTo "TATBD", "T" & ChrW(7855) & "t l" & ChrW(7899) & "p b" & ChrW(7843) & "n " & ChrW(273) & ChrW(7891), x, 374, 110
    ThemNutTo "BATBD", "B" & ChrW(7853) & "t l" & ChrW(7899) & "p b" & ChrW(7843) & "n " & ChrW(273) & ChrW(7891), x + 114, 374, 110

    ' Nap danh sach Tinh/Xa
    If NapMaXa(MAXA_PATH) Then
        Dim dS As Collection, i As Long
        Set dS = DsTinh()
        For i = 1 To dS.Count
            cboT.AddItem dS.Item(i)
        Next i
    End If

    ' Don vi hanh chinh da thiet lap (menu He thong) -> dien san
    Dim tinhLuu As String, xaLuu As String
    tinhLuu = DC_DocCauHinh("TINH", TINH_MD)
    cboT.Value = tinhLuu
    FillXa tinhLuu
    xaLuu = DC_DocCauHinh("XA", "")
    If Len(xaLuu) > 0 Then cboX.Value = xaLuu
    Me.Controls("txtHuyen").Text = DC_DocCauHinh("HUYEN", "")

    ' Tu dien CSDL theo ten file .dgn dang mo (dc01.dgn -> dc01.txt)
    Me.Controls("txtCSDL").Text = CsdlMacDinh()
    ' SUA 23/10: to ban do tu ten file dgn (DC9 -> 9)
    If Len(Trim$(Me.Controls("txtTo").Text)) = 0 Then Me.Controls("txtTo").Text = DC_ToTheoTenFile()

    ' Bat su kien doi Tinh -> loc Xa
    Set mCbo = New clsComboEvent
    Set mCbo.cbo = cboT
    Set mCbo.Form = Me

    ' SUA 11/10/2026: Mau ho so = Trich luc / Tach thua / Hop thua
    mLoai = -1
    Dim lo As Long
    lo = CLng(val(DC_DocCauHinh("LOAI_HS", "0")))
    If lo < 0 Or lo > 3 Then lo = 0
    Me.Controls("cboMauHS").ListIndex = lo
    MauHSDoi
    Set mCboHS = New clsComboEvent
    mCboHS.ma = "MAUHS"
    Set mCboHS.cbo = Me.Controls("cboMauHS")
    Set mCboHS.Form = Me
End Sub

' SUA 22/10: mau mac dinh - uu tien mau TT26 moi (cap nhat tu GitHub ve C:\DiaChinhVL\Mau)
Private Function MauMD(ByVal moi As String, ByVal cu As String, ByVal duoi As String) As String
    MauMD = "C:\DiaChinhVL\MAU\" & cu & "." & duoi
    On Error Resume Next
    If Len(Dir$("C:\DiaChinhVL\MAU\" & moi & "." & duoi)) > 0 Then MauMD = "C:\DiaChinhVL\MAU\" & moi & "." & duoi
End Function

' SUA 22/10 (ban 3.0): GHI CO DINH 4 mau TT26 theo thu tu danh sach (1 lan / may,
'   co MAU_TT26=1 trong DiaChinhVL.ini). Chi ghi khi file mau co trong C:\DiaChinhVL\MAU.
'   0 Trich luc ban do dia chinh -> trichluc ; 1 Tach -> PL22-tachthua ;
'   2 Hop -> PL22-hopthua ; 3 Phieu do dac chinh ly -> phieuchinhlydodac
'   Doi bo mau sau nay: tang so MAU_TT26 (vd "2") de cac may ghi lai.
Private Sub ChuyenMauTT26()
    Const PB As String = "1"
    If DC_DocCauHinh("MAU_TT26", "") = PB Then Exit Sub
    GhiMauTT26 "trichluc", "MAU_TL", "INI_TL0"
    If Len(Dir$("C:\DiaChinhVL\MAU\trichluc.ini")) > 0 Then DC_GhiCauHinh "INI_TL", "C:\DiaChinhVL\MAU\trichluc.ini"
    GhiMauTT26 "PL22-tachthua", "MAU_TACH", "INI_TACH"
    GhiMauTT26 "PL22-hopthua", "MAU_HOP", "INI_HOP"
    GhiMauTT26 "phieuchinhlydodac", "MAU_TL3", "INI_TL3"
    DC_GhiCauHinh "MAU_TT26", PB
End Sub

Private Sub GhiMauTT26(ByVal ten As String, ByVal kMau As String, ByVal kIni As String)
    Dim f As String
    On Error Resume Next
    f = "C:\DiaChinhVL\MAU\" & ten
    If Len(Dir$(f & ".dgn")) = 0 Then Exit Sub
    DC_GhiCauHinh kMau, f & ".dgn"
    If Len(Dir$(f & ".ini")) > 0 Then DC_GhiCauHinh kIni, f & ".ini"
End Sub

' Goi tu clsComboEvent khi doi "Mau ho so"
Public Sub MauHSDoi()
    Dim lo As Long
    lo = Me.Controls("cboMauHS").ListIndex
    If lo < 0 Then lo = 0
    If lo = mLoai Then Exit Sub
    If mLoai >= 0 Then LuuMau                 ' luu file mau cua loai cu
    mLoai = lo
    DC_GhiCauHinh "LOAI_HS", CStr(lo)
    Select Case lo
        Case 1
            Me.Controls("txtMau").Text = DC_DocCauHinh("MAU_TACH", MauMD("PL22-tachthua", "22tach", "dgn"))
            Me.Controls("txtIni").Text = DC_DocCauHinh("INI_TACH", MauMD("PL22-tachthua", "22tach", "ini"))
            Me.Controls("lbl_txtSoThua").Caption = "S" & ChrW(7889) & " th" & ChrW(7917) & "a c" & ChrW(7847) & "n t" & ChrW(225) & "ch:"
        Case 2
            Me.Controls("txtMau").Text = DC_DocCauHinh("MAU_HOP", MauMD("PL22-hopthua", "22hop", "dgn"))
            Me.Controls("txtIni").Text = DC_DocCauHinh("INI_HOP", MauMD("PL22-hopthua", "22hop", "ini"))
            Me.Controls("lbl_txtSoThua").Caption = "C" & ChrW(225) & "c th" & ChrW(7917) & "a h" & ChrW(7907) & "p (12,13):"
        Case 3
            ' SUA 16/10/2026: mau VL (Trich luc + Phieu do dac chinh ly), file rieng
            Me.Controls("txtMau").Text = DC_DocCauHinh("MAU_TL3", MauMD("phieuchinhlydodac", "trichluc", "dgn"))
            Me.Controls("txtIni").Text = DC_DocCauHinh("INI_TL3", MauMD("phieuchinhlydodac", "trichluc", "ini"))
            Me.Controls("lbl_txtSoThua").Caption = "S" & ChrW(7889) & " th" & ChrW(7917) & "a tr" & ChrW(237) & "ch l" & ChrW(7909) & "c:"
        Case Else
            Me.Controls("txtMau").Text = DC_DocCauHinh("MAU_TL", "C:\DiaChinhVL\TrichLucBanDo_mau.txt")
            Me.Controls("txtIni").Text = DC_DocCauHinh("INI_TL0", DC_DocCauHinh("INI_TL", ""))
            Me.Controls("lbl_txtSoThua").Caption = "S" & ChrW(7889) & " th" & ChrW(7917) & "a tr" & ChrW(237) & "ch l" & ChrW(7909) & "c:"
    End Select
    Me.Controls("txtLvCat").Enabled = (lo = 1)
    Me.Controls("lbl_lvcat").Enabled = (lo = 1)
    Me.Controls("chkMau").Enabled = (lo = 0 Or lo = 3)
End Sub

' Goi tu clsComboEvent khi doi Tinh
Public Sub TinhDoi()
    FillXa Me.Controls("cboTinh").Value
End Sub

Private Sub FillXa(ByVal tinh As String)
    Dim cboX As Object
    Set cboX = Me.Controls("cboXa")
    cboX.Clear
    Dim dS As Collection, i As Long
    Set dS = DsXa(tinh)
    For i = 1 To dS.Count
        cboX.AddItem dS.Item(i)
    Next i
    If dS.Count > 0 Then cboX.ListIndex = 0
End Sub

Private Sub AddPair(ByVal cap As String, ByVal nm As String, ByVal txt As String, _
                    ByVal x As Single, ByVal y As Single)
    AddLbl "lbl_" & nm, cap, x, y + 2, 100
    Dim c As Object
    Set c = Me.Controls.Add("Forms.TextBox.1", nm, True)
    c.Text = txt: c.Left = x + 104: c.Top = y: c.Width = 120: c.Height = 16
    c.Font.Name = "Arial": c.Font.size = 8
End Sub

Private Sub AddPairW(ByVal cap As String, ByVal nm As String, ByVal txt As String, _
                     ByVal x As Single, ByVal y As Single, ByVal w As Single)
    AddLbl "lbl_" & nm, cap, x, y + 2, 100
    Dim c As Object
    Set c = Me.Controls.Add("Forms.TextBox.1", nm, True)
    c.Text = txt: c.Left = x + 104: c.Top = y: c.Width = w: c.Height = 16
    c.Font.Name = "Arial": c.Font.size = 8
End Sub

' Ty le dung khi xuat: o go tay (neu co so) uu tien, sau do o chon (0 = Tu dong)
Private Function TyLeChon() As Double
    Dim v As Double
    v = val(Replace(Trim$(Me.Controls("txtTyLeTay").Text), ",", "."))
    If v <= 0 Then v = val(Me.Controls("cboTyLe").Value)
    TyLeChon = v
End Function

Private Sub AddLbl(ByVal nm As String, ByVal cap As String, _
                   ByVal x As Single, ByVal y As Single, ByVal w As Single)
    Dim c As Object
    Set c = Me.Controls.Add("Forms.Label.1", nm, True)
    c.Caption = cap: c.Left = x: c.Top = y: c.Width = w: c.Height = 14
    c.Font.Name = "Arial": c.Font.size = 8
End Sub

Private Sub ThemNutNho(ByVal ma As String, ByVal cap As String, ByVal x As Single, ByVal y As Single)
    Dim b As Object, h As clsNutTL
    Set b = Me.Controls.Add("Forms.CommandButton.1", "cmd" & ma, True)
    b.Caption = cap: b.Left = x: b.Top = y: b.Width = 22: b.Height = 16
    b.Font.Name = "Arial": b.Font.size = 8
    Set h = New clsNutTL: Set h.btn = b: Set h.Form = Me: h.ma = ma: mNut.Add h
End Sub

Private Sub ThemDongLevel(ByVal nmChk As String, ByVal cap As String, ByVal nmTxt As String, _
                          ByVal txt As String, ByVal bat As Boolean, ByVal maXoa As String, _
                          ByVal x As Single, ByVal y As Single)
    Dim c As Object, t As Object, b As Object, h As clsNutTL
    Set c = Me.Controls.Add("Forms.CheckBox.1", nmChk, True)
    c.Caption = cap: c.Left = x: c.Top = y: c.Width = 100: c.Height = 16: c.Value = bat
    c.Font.Name = "Arial": c.Font.size = 8
    Set t = Me.Controls.Add("Forms.TextBox.1", nmTxt, True)
    t.Text = txt: t.Left = x + 104: t.Top = y: t.Width = 136: t.Height = 16
    t.Font.Name = "Arial": t.Font.size = 8
    Set b = Me.Controls.Add("Forms.CommandButton.1", "cmd" & maXoa, True)
    b.Caption = "X" & ChrW(243) & "a": b.Left = x + 250: b.Top = y - 1: b.Width = 44: b.Height = 18
    b.Font.Name = "Arial": b.Font.size = 8
    Set h = New clsNutTL: Set h.btn = b: Set h.Form = Me: h.ma = maXoa: mNut.Add h
End Sub

Private Sub ThemNutTo(ByVal ma As String, ByVal cap As String, ByVal x As Single, ByVal y As Single, ByVal w As Single)
    Dim b As Object, h As clsNutTL
    Set b = Me.Controls.Add("Forms.CommandButton.1", "cmd" & ma, True)
    b.Caption = cap: b.Left = x: b.Top = y: b.Width = w: b.Height = 22
    b.Font.Name = "Arial": b.Font.size = 8
    Set h = New clsNutTL: Set h.btn = b: Set h.Form = Me: h.ma = ma: mNut.Add h
End Sub

Private Sub LuuLevel()
    DC_GhiCauHinh "LV_HS", Trim$(Me.Controls("txtLvHS").Text)
    DC_GhiCauHinh "LV_SD", Trim$(Me.Controls("txtLvSD").Text)
    DC_GhiCauHinh "LV_HS_ON", IIf(Me.Controls("chkLvHS").Value, "1", "0")
    DC_GhiCauHinh "LV_SD_ON", IIf(Me.Controls("chkLvSD").Value, "1", "0")
End Sub

Private Sub LuuMau()
    Dim hau As String
    Select Case mLoai
        Case 1: hau = "TACH"
        Case 2: hau = "HOP"
        Case 3: hau = "TL3"
        Case Else: hau = "TL"
    End Select
    DC_GhiCauHinh "MAU_" & hau, Trim$(Me.Controls("txtMau").Text)
    If mLoai = 0 Then
        ' INI_TL = ini DANG DUNG khi xuat trich luc (modMauDgn doc); moi mau luu rieng
        DC_GhiCauHinh "INI_TL0", Trim$(Me.Controls("txtIni").Text)
    Else
        DC_GhiCauHinh "INI_" & hau, Trim$(Me.Controls("txtIni").Text)
    End If
    If mLoai = 0 Or mLoai = 3 Then DC_GhiCauHinh "INI_TL", Trim$(Me.Controls("txtIni").Text)
    If mLoai = 1 Then DC_GhiCauHinh "TACH_LV", Trim$(Me.Controls("txtLvCat").Text)
End Sub

Private Sub LuuDonViHC()
    DC_GhiCauHinh "TINH", CStr(Me.Controls("cboTinh").Value)
    DC_GhiCauHinh "XA", CStr(Me.Controls("cboXa").Value)
    DC_GhiCauHinh "HUYEN", Me.Controls("txtHuyen").Text
End Sub

Public Sub XuLyNut(ByVal ma As String)
    If ma = "DONG" Then LuuViTri: Unload Me: Exit Sub
    If ma = "CHONMAU" Then
        Dim f As String
        f = DC_ChonFile("File m" & ChrW(7851) & "u (*.dgn;*.txt)|*.dgn;*.txt|T" & ChrW(7845) & "t c" & ChrW(7843) & "|*.*", "Chon file mau trich luc", Me.Controls("txtMau").Text)
        If Len(f) > 0 Then Me.Controls("txtMau").Text = f: LuuMau
        Exit Sub
    End If
    If ma = "CHONINI" Then
        Dim g As String
        g = DC_ChonFile("File c" & ChrW(7845) & "u h" & ChrW(236) & "nh (*.ini)|*.ini|T" & ChrW(7845) & "t c" & ChrW(7843) & "|*.*", "Chon file cau hinh", Me.Controls("txtIni").Text)
        If Len(g) > 0 Then Me.Controls("txtIni").Text = g: LuuMau
        Exit Sub
    End If
    If ma = "TATBD" Then LuuLevel: DC_TatLopBanDo Trim$(Me.Controls("txtLvHS").Text), Trim$(Me.Controls("txtLvSD").Text): Exit Sub
    If ma = "BATBD" Then DC_BatLopBanDo: Exit Sub
    If ma = "XOAHS" Then DC_XoaTheoLevel Trim$(Me.Controls("txtLvHS").Text): Exit Sub
    If ma = "XOASD" Then DC_XoaTheoLevel Trim$(Me.Controls("txtLvSD").Text): Exit Sub
    LuuLevel
    If ma = "LUUHS" Then
        DC_LuuFileHoSo Trim$(Me.Controls("txtLvHS").Text), Trim$(Me.Controls("txtLvSD").Text)
        Exit Sub
    End If
    LuuMau
    DC_GhiCauHinh "TL_TYLE", IIf(val(Me.Controls("cboTyLe").Value) > 0, CStr(val(Me.Controls("cboTyLe").Value)), "")
    DC_GhiCauHinh "TL_TYLE_TAY", IIf(val(Me.Controls("txtTyLeTay").Text) > 0, CStr(val(Me.Controls("txtTyLeTay").Text)), "")
    If mLoai = 1 Or mLoai = 2 Then XuLyTachHop ma: Exit Sub
    If ma = "CHON" Then
        If DC_DaTatLop() Then DC_BatLopBanDo     ' hien lai ban do de bam chon thua
        LuuDonViHC
        LuuViTri
        Me.Hide
        DC_ChonThuaTrichLuc Me.Controls("txtCSDL").Text, _
                 Me.Controls("txtMau").Text, Me.Controls("txtKieu").Text, _
                 Me.Controls("txtTo").Text, CStr(Me.Controls("cboXa").Value), _
                 Me.Controls("txtHuyen").Text, CStr(Me.Controls("cboTinh").Value), _
                 "", val(Me.Controls("txtCao").Text), _
                 Me.Controls("chkMau").Value, TyLeChon()
        Exit Sub
    End If
    If Len(Trim$(Me.Controls("txtSoThua").Text)) = 0 Then
        MsgBox "Nh" & ChrW(7853) & "p s" & ChrW(7889) & " th" & ChrW(7917) & "a c" & ChrW(7847) & "n tr" & ChrW(237) & "ch l" & ChrW(7909) & "c.", vbExclamation: Exit Sub
    End If
    LuuDonViHC                         ' nho lai don vi hanh chinh vua dung
    LuuViTri
    Me.Hide
    ChayTrichLuc Me.Controls("txtCSDL").Text, Me.Controls("txtSoThua").Text, _
                 Me.Controls("txtMau").Text, Me.Controls("txtKieu").Text, _
                 Me.Controls("txtTo").Text, CStr(Me.Controls("cboXa").Value), _
                 Me.Controls("txtHuyen").Text, CStr(Me.Controls("cboTinh").Value), _
                 "", val(Me.Controls("txtCao").Text), _
                 Me.Controls("chkMau").Value, TyLeChon()
    Me.Show vbModeless
End Sub

' Tach / hop thua: "Chon thua" (bam tren ban do) hoac "Chap nhan" (go so thua)
Private Sub XuLyTachHop(ByVal ma As String)
    Dim tieuDe As String
    If mLoai = 2 Then tieuDe = "H" & ChrW(7907) & "p th" & ChrW(7917) & "a" Else tieuDe = "T" & ChrW(225) & "ch th" & ChrW(7917) & "a"
    LuuDonViHC
    If ma = "CHON" Then
        If DC_DaTatLop() Then DC_BatLopBanDo     ' hien lai ban do de bam chon thua
        LuuViTri
        Me.Hide
        DC_ChonThuaTrichLuc Me.Controls("txtCSDL").Text, Me.Controls("txtMau").Text, "T", _
                 Me.Controls("txtTo").Text, CStr(Me.Controls("cboXa").Value), _
                 Me.Controls("txtHuyen").Text, CStr(Me.Controls("cboTinh").Value), _
                 "", 1, True, TyLeChon(), _
                 mLoai, Me.Controls("txtIni").Text, Me.Controls("txtLvCat").Text
        Exit Sub
    End If
    If Len(Trim$(Me.Controls("txtSoThua").Text)) = 0 Then
        DC_ThongBao IIf(mLoai = 2, "Nh" & ChrW(7853) & "p c" & ChrW(225) & "c s" & ChrW(7889) & " th" & ChrW(7917) & "a c" & ChrW(7847) & "n h" & ChrW(7907) & "p (vd 12,13) ho" & ChrW(7863) & "c b" & ChrW(7845) & "m Ch" & ChrW(7885) & "n th" & ChrW(7917) & "a.", _
                    "Nh" & ChrW(7853) & "p s" & ChrW(7889) & " th" & ChrW(7917) & "a c" & ChrW(7847) & "n t" & ChrW(225) & "ch ho" & ChrW(7863) & "c b" & ChrW(7845) & "m Ch" & ChrW(7885) & "n th" & ChrW(7917) & "a."), tieuDe, vbExclamation
        Exit Sub
    End If
    Dim goc As Collection, Loi As String
    Set goc = DC_LayThuaCSDL(Me.Controls("txtCSDL").Text, Me.Controls("txtSoThua").Text, Loi)
    If goc Is Nothing Then DC_ThongBao Loi, tieuDe, vbExclamation: Exit Sub
    LuuViTri
    Me.Hide
    DC_ChayTachHop mLoai, goc, Me.Controls("txtMau").Text, Me.Controls("txtIni").Text, _
                   Me.Controls("txtTo").Text, CStr(Me.Controls("cboXa").Value), _
                   Me.Controls("txtHuyen").Text, CStr(Me.Controls("cboTinh").Value), _
                   TyLeChon(), Me.Controls("txtLvCat").Text
    Me.Show vbModeless
End Sub

' SUA 12/10/2026: nho vi tri form -> mo lai (sau Chon thua...) dung cho cu
Private Sub LuuViTri()
    DC_GhiCauHinh "TL_LEFT", CStr(CLng(Me.Left))
    DC_GhiCauHinh "TL_TOP", CStr(CLng(Me.Top))
End Sub

Private Sub UserForm_Activate()
    Dim L As String, t As String
    L = DC_DocCauHinh("TL_LEFT", ""): t = DC_DocCauHinh("TL_TOP", "")
    If Len(L) > 0 And Len(t) > 0 Then
        Me.StartUpPosition = 0
        Me.Left = val(L): Me.Top = val(t)
    End If
End Sub

Private Sub UserForm_QueryClose(Cancel As Integer, CloseMode As Integer)
    LuuViTri
End Sub

Attribute VB_Name = "frmTroLy"
Attribute VB_Base = "0{A8AF184F-2CE2-4C9D-B9C7-CDDA616561C0}{057DA365-6553-436D-B02E-1BB984EDA4FC}"
Attribute VB_GlobalNameSpace = False
Attribute VB_Creatable = False
Attribute VB_PredeclaredId = True
Attribute VB_Exposed = False
Attribute VB_TemplateDerived = False
Attribute VB_Customizable = False
'============================================================
' frmTroLy - Tro ly lenh: go cau lenh tieng Viet -> phan mem tu lam
'   Can: modTroLy, clsNutTL, modCauHinh. Tao bang DC_MoFormTuTao.
'============================================================
Option Explicit

Private mNut As New Collection

Private Sub UserForm_Initialize()
    Dim c As Object
    Me.Caption = "Tro ly lenh DiaChinhVL"
    Me.Width = 420: Me.Height = 330
    Me.Font.Name = "Arial": Me.Font.size = 8

    Set c = Me.Controls.Add("Forms.Label.1", "lblMau", True)
    c.Left = 8: c.Top = 4: c.Width = 400: c.Height = 14: c.Font.Name = "Arial": c.Font.size = 9: c.Font.Bold = True
    c.ForeColor = &H800000

    Set c = Me.Controls.Add("Forms.Label.1", "lblHD", True)
    c.Caption = "G" & ChrW(245) & " vi" & ChrW(7879) & "c c" & ChrW(7847) & "n l" & ChrW(224) & "m b" & ChrW(7857) & "ng ti" & ChrW(7871) & "ng Vi" & ChrW(7879) & "t (nhi" & ChrW(7873) & "u vi" & ChrW(7879) & "c c" & ChrW(225) & "ch nhau b" & ChrW(7857) & "ng d" & ChrW(7845) & "u ; ho" & ChrW(7863) & "c xu" & ChrW(7889) & "ng d" & ChrW(242) & "ng), r" & ChrW(7891) & "i b" & ChrW(7845) & "m Th" & ChrW(7921) & "c hi" & ChrW(7879) & "n:"
    c.Left = 8: c.Top = 20: c.Width = 400: c.Height = 14: c.Font.Name = "Arial": c.Font.size = 8

    Set c = Me.Controls.Add("Forms.TextBox.1", "txtLenh", True)
    c.Left = 8: c.Top = 36: c.Width = 398: c.Height = 52
    c.MultiLine = True: c.EnterKeyBehavior = True: c.WordWrap = True
    c.Font.Name = "Arial": c.Font.size = 10
    c.Text = DC_DocCauHinh("AI_LENH" & gTLMau, TL_ViDu(gTLMau))

    Set c = Me.Controls.Add("Forms.Label.1", "lblVD", True)
    c.Caption = "V" & ChrW(237) & " d" & ChrW(7909) & ": t" & ChrW(7841) & "o v" & ChrW(249) & "ng l" & ChrW(7899) & "p 10 " & ChrW(183) & " g" & ChrW(225) & "n th" & ChrW(7917) & "a l" & ChrW(7899) & "p 13 " & ChrW(183) & " g" & ChrW(225) & "n lo" & ChrW(7841) & "i " & ChrW(273) & ChrW(7845) & "t l" & ChrW(7899) & "p 6 " & ChrW(183) & " tr" & ChrW(237) & "ch l" & ChrW(7909) & "c th" & ChrW(7917) & "a 15 t" & ChrW(7927) & " l" & ChrW(7879) & " 500 " & ChrW(183) & " t" & ChrW(225) & "ch th" & ChrW(7917) & "a 15 l" & ChrW(7899) & "p c" & ChrW(7855) & "t 18 " & ChrW(183) & " h" & ChrW(7907) & "p th" & ChrW(7917) & "a 12, 13 " & ChrW(183) & " t" & ChrW(244) & " m" & ChrW(224) & "u " & ChrW(183) & " xu" & ChrW(7845) & "t polygon " & ChrW(183) & " chi" & ChrW(7873) & "u d" & ChrW(224) & "i c" & ChrW(7841) & "nh " & ChrW(183) & " t" & ChrW(7855) & "t l" & ChrW(7899) & "p " & ChrW(183) & " l" & ChrW(432) & "u h" & ChrW(7891) & " s" & ChrW(417)
    c.Left = 8: c.Top = 92: c.Width = 400: c.Height = 26: c.WordWrap = True
    c.Font.Name = "Arial": c.Font.size = 7: c.ForeColor = &H808080

    Set c = Me.Controls.Add("Forms.TextBox.1", "txtKQ", True)
    c.Left = 8: c.Top = 120: c.Width = 398: c.Height = 146
    c.MultiLine = True: c.ScrollBars = 2: c.Locked = True: c.BackColor = &HF4F4F4
    c.Font.Name = "Arial": c.Font.size = 8

    ThemNut "CHAY", "Th" & ChrW(7921) & "c hi" & ChrW(7879) & "n", 240, 274, 80
    ThemNut "DONG", ChrW(272) & ChrW(243) & "ng", 326, 274, 80
    HienMau
End Sub

Private Sub UserForm_Activate()
    HienMau
End Sub

' Cap nhat tieu de theo mau dang chon (mo lai tu menu mau khac)
Private Sub HienMau()
    Static mCu As Long, daCo As Boolean
    On Error Resume Next
    Me.Controls("lblMau").Caption = "M" & ChrW(7851) & "u: " & TL_TenMau(gTLMau)
    If daCo And mCu <> gTLMau Then Me.Controls("txtLenh").Text = DC_DocCauHinh("AI_LENH" & gTLMau, TL_ViDu(gTLMau))
    mCu = gTLMau: daCo = True
End Sub

Public Sub XuLyNut(ByVal ma As String)
    If ma = "DONG" Then Unload Me: Exit Sub
    Dim lenh As String, kq As String
    lenh = Me.Controls("txtLenh").Text
    DC_GhiCauHinh "AI_LENH" & gTLMau, Replace(Replace(lenh, vbCr, " "), vbLf, " ")
    Me.Controls("txtKQ").Text = ChrW(272) & "ang ch" & ChrW(7841) & "y ..."
    Me.Hide
    kq = TL_ChayLenh(lenh)
    Me.Show vbModeless
    Me.Controls("txtKQ").Text = kq
End Sub

Private Sub ThemNut(ByVal ma As String, ByVal cap As String, ByVal x As Single, ByVal y As Single, ByVal w As Single)
    Dim b As Object, hd As clsNutTL
    Set b = Me.Controls.Add("Forms.CommandButton.1", "cmd" & ma, True)
    b.Caption = cap: b.Left = x: b.Top = y: b.Width = w: b.Height = 22
    b.Font.Name = "Arial": b.Font.size = 8
    Set hd = New clsNutTL
    Set hd.btn = b: Set hd.Form = Me: hd.ma = ma
    mNut.Add hd
End Sub

Attribute VB_Name = "frmVeNhan"
Attribute VB_Base = "0{2918C7A4-2D32-42A5-92B6-81D72C390360}{299C72E3-B0DB-4FC9-85DF-B6BA6F2791D5}"
Attribute VB_GlobalNameSpace = False
Attribute VB_Creatable = False
Attribute VB_PredeclaredId = True
Attribute VB_Exposed = False
Attribute VB_TemplateDerived = False
Attribute VB_Customizable = False
'============================================================
' frmVeNhan - "Ve nhan thua" (giong gCadas/LandMap) - nhan TT26 thanh khoi
'   Can: modVeNhan, modChieuDai (CDC_DsLevel), clsNutTL, modCauHinh.
'   Mo bang DC_MoFormTuTao "frmVeNhan".
'============================================================
Option Explicit

Private mNut As New Collection

Private Sub UserForm_Initialize()
    Dim c As Object, tL As Variant
    Me.Caption = "Ve nhan thua"
    Me.Width = 330: Me.Height = 330
    Me.Font.Name = "Arial": Me.Font.size = 8

    Nhan "File CSDL:", 8, 8, 60
    Set c = Me.Controls.Add("Forms.TextBox.1", "txtCSDL", True)
    c.Left = 70: c.Top = 6: c.Width = 248: c.Height = 16: c.Font.Name = "Arial": c.Font.size = 8
    c.Text = CsdlMacDinh()

    Khung "Thu" & ChrW(7897) & "c t" & ChrW(237) & "nh nh" & ChrW(227) & "n", 4, 28, 316
    Nhan "T" & ChrW(7927) & " l" & ChrW(7879) & " b" & ChrW(7843) & "n " & ChrW(273) & ChrW(7891) & "   1:", 12, 48, 80
    Set c = Me.Controls.Add("Forms.ComboBox.1", "cboTyLe", True)
    c.Left = 96: c.Top = 46: c.Width = 70: c.Height = 16: c.Font.Name = "Arial": c.Font.size = 8
    For Each tL In Array("200", "500", "1000", "2000", "5000", "10000")
        c.AddItem tL
    Next tL
    c.Text = DC_DocCauHinh("VN_TYLE", "2000")
    Nhan "S" & ChrW(7889) & " l" & ChrW(7867), 180, 48, 40
    Set c = Me.Controls.Add("Forms.ComboBox.1", "cboLe", True)
    c.Left = 220: c.Top = 46: c.Width = 50: c.Height = 16: c.Font.Name = "Arial": c.Font.size = 8
    c.AddItem "0": c.AddItem "0.0": c.AddItem "0.00"
    c.Text = DC_DocCauHinh("VN_LE", "0.0")
    Nhan "C" & ChrW(7905) & " ch" & ChrW(7919) & " (mm)", 12, 70, 80
    o "txtCao", DC_DocCauHinh("VN_CAO", "1.2"), 96, 68, 34
    o "txtRong", DC_DocCauHinh("VN_RONG", "1.2"), 134, 68, 34
    Nhan "(cao, r" & ChrW(7897) & "ng)", 172, 70, 60
    chon "chkPhay", "Di" & ChrW(7879) & "n t" & ChrW(237) & "ch d" & ChrW(7845) & "u ph" & ChrW(7849) & "y", 12, 90, 110, DC_DocCauHinh("VN_PHAY", "1") = "1"
    chon "chkNghieng", "Ch" & ChrW(7919) & " nghi" & ChrW(234) & "ng", 126, 90, 80, DC_DocCauHinh("VN_NGHIENG", "0") = "1"
    chon "chkHa", ChrW(272) & ChrW(7893) & "i (ha)", 210, 90, 70, DC_DocCauHinh("VN_HA", "0") = "1"

    Khung "Tu" & ChrW(7923) & " ch" & ChrW(7885) & "n nh" & ChrW(227) & "n  (l" & ChrW(7899) & "p - m" & ChrW(224) & "u)", 4, 114, 316
    Dong "S" & ChrW(7889) & " hi" & ChrW(7879) & "u th" & ChrW(7917) & "a", "cboLvSo", "txtMauSo", DC_DocCauHinh("VN_LVSO", "Level 13"), DC_DocCauHinh("VN_MAUSO", "1"), 134
    Dong "Di" & ChrW(7879) & "n t" & ChrW(237) & "ch th" & ChrW(7917) & "a", "cboLvDt", "txtMauDt", DC_DocCauHinh("VN_LVDT", "Level 4"), DC_DocCauHinh("VN_MAUDT", "2"), 156
    Dong "Lo" & ChrW(7841) & "i " & ChrW(273) & ChrW(7845) & "t", "cboLvLoai", "txtMauLoai", DC_DocCauHinh("VN_LVLOAI", "Level 2"), DC_DocCauHinh("VN_MAULOAI", "5"), 178

    Khung "Ph" & ChrW(7841) & "m vi s" & ChrW(7889) & " th" & ChrW(7917) & "a  (" & ChrW(273) & ChrW(7875) & " tr" & ChrW(7889) & "ng = t" & ChrW(7845) & "t c" & ChrW(7843) & ")", 4, 202, 316
    Nhan "T" & ChrW(7915) & " th" & ChrW(7917) & "a", 12, 222, 50
    o "txtTu", "", 64, 220, 50
    Nhan ChrW(272) & ChrW(7871) & "n th" & ChrW(7917) & "a", 130, 222, 50
    o "txtDen", "", 184, 220, 50

    Nhan "M" & ChrW(7895) & "i nh" & ChrW(227) & "n = 1 kh" & ChrW(7889) & "i (lo" & ChrW(7841) & "i " & ChrW(273) & ChrW(7845) & "t, s" & ChrW(7889) & " th" & ChrW(7917) & "a / di" & ChrW(7879) & "n t" & ChrW(237) & "ch) theo Th" & ChrW(244) & "ng t" & ChrW(432) & " 26.", 8, 246, 312
    ThemNut "VE", "V" & ChrW(7869) & " nh" & ChrW(227) & "n", 8, 266, 96
    ThemNut "XOA", "X" & ChrW(243) & "a nh" & ChrW(227) & "n", 112, 266, 96
    ThemNut "DONG", ChrW(272) & ChrW(243) & "ng", 222, 266, 96
End Sub

Public Sub XuLyNut(ByVal ma As String)
    Dim n As Long, Loi As String, tieuDe As String
    tieuDe = "V" & ChrW(7869) & " nh" & ChrW(227) & "n th" & ChrW(7917) & "a"
    Select Case ma
        Case "DONG": Unload Me
        Case "XOA"
            n = VN_XoaNhan()
            DC_ThongBao ChrW(272) & ChrW(227) & " x" & ChrW(243) & "a " & n & " nh" & ChrW(227) & "n th" & ChrW(7917) & "a (kh" & ChrW(7889) & "i NHANTHUA).", tieuDe
        Case "VE"
            Luu
            n = VN_VeNhan(Me.Controls("txtCSDL").Text, so("cboTyLe"), so("txtCao"), so("txtRong"), _
                          SoLe(), Me.Controls("chkPhay").Value, Me.Controls("chkNghieng").Value, _
                          Me.Controls("chkHa").Value, Me.Controls("cboLvSo").Text, CLng(so("txtMauSo")), _
                          Me.Controls("cboLvDt").Text, CLng(so("txtMauDt")), Me.Controls("cboLvLoai").Text, _
                          CLng(so("txtMauLoai")), Me.Controls("txtTu").Text, Me.Controls("txtDen").Text, Loi)
            If Len(Loi) > 0 Then
                DC_ThongBao Loi, tieuDe, vbExclamation
            Else
                DC_ThongBao ChrW(272) & ChrW(227) & " v" & ChrW(7869) & " " & n & " nh" & ChrW(227) & "n th" & ChrW(7917) & "a." & vbCrLf & "(V" & ChrW(7869) & " l" & ChrW(7841) & "i: b" & ChrW(7845) & "m X" & ChrW(243) & "a nh" & ChrW(227) & "n tr" & ChrW(432) & ChrW(7899) & "c)", tieuDe
            End If
    End Select
End Sub

Private Function so(ByVal nm As String) As Double
    so = val(Replace(Trim$(Me.Controls(nm).Text), ",", "."))
End Function

Private Function SoLe() As Long
    Dim s As String
    s = Trim$(Me.Controls("cboLe").Text)
    If InStr(s, ".") > 0 Then SoLe = Len(s) - InStr(s, ".") Else SoLe = 0
End Function

Private Sub Luu()
    DC_GhiCauHinh "VN_TYLE", Me.Controls("cboTyLe").Text
    DC_GhiCauHinh "VN_LE", Me.Controls("cboLe").Text
    DC_GhiCauHinh "VN_CAO", Me.Controls("txtCao").Text
    DC_GhiCauHinh "VN_RONG", Me.Controls("txtRong").Text
    DC_GhiCauHinh "VN_PHAY", IIf(Me.Controls("chkPhay").Value, "1", "0")
    DC_GhiCauHinh "VN_NGHIENG", IIf(Me.Controls("chkNghieng").Value, "1", "0")
    DC_GhiCauHinh "VN_HA", IIf(Me.Controls("chkHa").Value, "1", "0")
    DC_GhiCauHinh "VN_LVSO", Me.Controls("cboLvSo").Text
    DC_GhiCauHinh "VN_MAUSO", Me.Controls("txtMauSo").Text
    DC_GhiCauHinh "VN_LVDT", Me.Controls("cboLvDt").Text
    DC_GhiCauHinh "VN_MAUDT", Me.Controls("txtMauDt").Text
    DC_GhiCauHinh "VN_LVLOAI", Me.Controls("cboLvLoai").Text
    DC_GhiCauHinh "VN_MAULOAI", Me.Controls("txtMauLoai").Text
End Sub

'------------------------------------------------------------ tao control
Private Sub Khung(ByVal cap As String, ByVal x As Single, ByVal y As Single, ByVal w As Single)
    Dim c As Object
    Set c = Me.Controls.Add("Forms.Label.1")
    c.Caption = cap: c.Left = x: c.Top = y: c.Width = w: c.Height = 13
    c.Font.Name = "Arial": c.Font.size = 8: c.Font.Bold = True
    c.BackColor = &HF0E0D0: c.BackStyle = 1
End Sub

Private Sub Nhan(ByVal cap As String, ByVal x As Single, ByVal y As Single, ByVal w As Single)
    Dim c As Object
    Set c = Me.Controls.Add("Forms.Label.1")
    c.Caption = cap: c.Left = x: c.Top = y: c.Width = w: c.Height = 12
    c.Font.Name = "Arial": c.Font.size = 8
End Sub

Private Sub o(ByVal nm As String, ByVal gt As String, ByVal x As Single, ByVal y As Single, ByVal w As Single)
    Dim c As Object
    Set c = Me.Controls.Add("Forms.TextBox.1", nm, True)
    c.Left = x: c.Top = y: c.Width = w: c.Height = 16
    c.Font.Name = "Arial": c.Font.size = 8: c.TextAlign = 3
    c.Text = gt
End Sub

' 1 dong: nhan | combo level | "Mau" | o mau
Private Sub Dong(ByVal cap As String, ByVal nmLv As String, ByVal nmMau As String, _
                 ByVal lv As String, ByVal mau As String, ByVal y As Single)
    Dim c As Object, dS As Collection, i As Long
    Nhan cap, 12, y + 2, 84
    Set c = Me.Controls.Add("Forms.ComboBox.1", nmLv, True)
    c.Left = 96: c.Top = y: c.Width = 130: c.Height = 16: c.Font.Name = "Arial": c.Font.size = 8
    Set dS = CDC_DsLevel()
    For i = 1 To dS.Count: c.AddItem dS(i): Next i
    c.Text = lv
    Nhan "M" & ChrW(224) & "u", 236, y + 2, 26
    o nmMau, mau, 264, y, 40
End Sub

Private Sub chon(ByVal nm As String, ByVal cap As String, ByVal x As Single, ByVal y As Single, ByVal w As Single, ByVal v As Boolean)
    Dim c As Object
    Set c = Me.Controls.Add("Forms.CheckBox.1", nm, True)
    c.Caption = cap: c.Left = x: c.Top = y: c.Width = w: c.Height = 16
    c.Font.Name = "Arial": c.Font.size = 8
    c.Value = v
End Sub

Private Sub ThemNut(ByVal ma As String, ByVal cap As String, ByVal x As Single, ByVal y As Single, ByVal w As Single)
    Dim b As Object, hd As clsNutTL
    Set b = Me.Controls.Add("Forms.CommandButton.1", "cmd" & ma, True)
    b.Caption = cap: b.Left = x: b.Top = y: b.Width = w: b.Height = 24
    b.Font.Name = "Arial": b.Font.size = 8
    Set hd = New clsNutTL
    Set hd.btn = b: Set hd.Form = Me: hd.ma = ma
    mNut.Add hd
End Sub

Attribute VB_Name = "modBang8"
'============================================================
' modBang8 - GHI BANG TOA DO DINH THUA (muc 8) - Phu luc 19
' Du an: DiaChinhVL  (MicroStation V8i - MVBA)
'
' Thay the doan ghi bang muc 8 cu. Sua 3 loi:
'   1. Cot X(m) va Y(m) de len nhau  -> moi cot co TAM X rieng
'   2. Cot "Kich thuoc canh" lech nua dong -> canh giua dung dong
'   3. Tieu de "Toa do dinh thua" va "Kich thuoc canh (m)" de nhau
'
' Nguyen tac: KHONG dat chu theo offset cong don nua.
' Moi chu duoc dat CenterCenter vao TAM O = giua 2 duong ke.
' Chu qua dai se TU DONG thu nho de vua be rong cot.
'============================================================
Option Explicit

'==================================================================
' PHAN 1 - HINH HOC BANG   (CHI CAN SUA O DAY)
'------------------------------------------------------------------
' Tat ca so do la KHOANG CACH tinh tu GOC CHEN KHUNG MAU (dOx, dOy),
' don vi: met (master unit).
'
' CACH DO 1 LAN CHO XONG:
'   1. Mo 1 to .dgn da chen khung mau.
'   2. Dung menu Utilities > Key-in, danh: ANALYZE ELEMENT  (hoac
'      dung Tools > Primary > "ID point") roi bam vao cac GIAO DIEM
'      duong ke cua bang muc 8, ghi lai toa do X, Y.
'   3. Lay toa do do TRU DI toa do goc chen khung -> dien vao duoi.
'
' Neu khung mau cua ban luon chen tai cung mot cho, co the goi
' GhiBangDinhThua ring, 0, 0  va dien truc tiep toa do that.
'==================================================================

' --- X: 5 duong ke DOC cua bang (tu trai sang phai) ---
Private Const C_BIEN0 As Double = 60#    ' bien TRAI cot "Dinh"
Private Const C_BIEN1 As Double = 68#    ' vach  Dinh | X(m)
Private Const C_BIEN2 As Double = 92#    ' vach  X(m) | Y(m)
Private Const C_BIEN3 As Double = 116#   ' vach  Y(m) | Canh
Private Const C_BIEN4 As Double = 140#   ' bien PHAI cot Canh

' --- Y: cac duong ke NGANG ---
Private Const C_YDAU As Double = -40#    ' duong ke TREN cua DONG DU LIEU 1
Private Const C_CAODONG As Double = 4#   ' chieu cao 1 dong du lieu
Private Const C_SODONG As Long = 18      ' so dong trong bang mau

' --- Y: hai dong tieu de (nam PHIA TREN C_YDAU) ---
Private Const C_CAO_TD2 As Double = 4#   ' dong "X(m) | Y(m)"
Private Const C_CAO_TD1 As Double = 5#   ' dong "Toa do dinh thua"

' --- Chu ---
Private Const C_CAOCHU As Double = 2#    ' chieu cao chu trong bang
Private Const C_CAOCHU_TD As Double = 2# ' chieu cao chu tieu de
Private Const C_LEVEL As Long = 24       ' level ghi bang (nhu so do thua)

' Uoc luong be rong 1 ky tu = C_TILE_RONG * chieu cao chu.
' Times New Roman chu so ~ 0.5 ; de 0.62 cho an toan.
Private Const C_TILE_RONG As Double = 0.62

' True  = so canh nam GIUA hai dong (dinh i va dinh i+1)  <- kieu bang cu
' False = so canh canh giua DUNG dong cua dinh i          <- MAC DINH (da sua)
Private Const C_CANH_GIUA_HAI_DONG As Boolean = False

' True = ghi ca tieu de bang. Neu khung mau da co san tieu de
'        (chu in san trong file mau) thi de False cho khoi de chu.
Private Const C_GHI_TIEU_DE As Boolean = True

' True = dung chu co dau (can font Times New Roman + Save Settings)
Private Const C_CO_DAU As Boolean = False


'==================================================================
' PHAN 2 - HAM CHINH
'------------------------------------------------------------------
' ring()  : mang 2 chieu Double, ring(i,0)=X  ring(i,1)=Y  (met, VN2000)
'           Chap nhan ca ring DONG (diem cuoi = diem dau) - se tu bo
'           diem trung lap.
' dOx,dOy : toa do GOC CHEN KHUNG MAU cua to nay.
'==================================================================
Public Sub GhiBangDinhThua(ring() As Double, ByVal dOx As Double, ByVal dOy As Double)

    Dim lo As Long, hi As Long, soDinh As Long
    Dim i As Long, j As Long
    Dim xTam(1 To 4) As Double, rongCot(1 To 4) As Double
    Dim yTam As Double, yCanh As Double
    Dim x1 As Double, y1 As Double, x2 As Double, y2 As Double
    Dim dCanh As Double

    On Error GoTo LoiRoi

    '--- 2.1 Xac dinh so dinh (bo diem dong vong) ---
    lo = LBound(ring, 1)
    hi = UBound(ring, 1)
    If hi - lo + 1 < 3 Then
        MsgBox "Ranh thua khong du 3 dinh, khong ghi duoc bang toa do.", _
               vbExclamation, "Bang toa do"
        Exit Sub
    End If
    If Abs(ring(hi, 0) - ring(lo, 0)) < 0.001 And _
       Abs(ring(hi, 1) - ring(lo, 1)) < 0.001 Then
        hi = hi - 1                     ' ring dong -> bo diem cuoi
    End If
    soDinh = hi - lo + 1

    If soDinh > C_SODONG Then
        MsgBox "Thua co " & soDinh & " dinh nhung bang mau chi co " & _
               C_SODONG & " dong." & vbCrLf & _
               "Se ghi " & C_SODONG & " dinh dau tien.", _
               vbExclamation, "Bang toa do"
        soDinh = C_SODONG
    End If

    '--- 2.2 Tam X va be rong tung cot (day la cho sua loi X/Y de nhau) ---
    xTam(1) = dOx + (C_BIEN0 + C_BIEN1) / 2#
    xTam(2) = dOx + (C_BIEN1 + C_BIEN2) / 2#
    xTam(3) = dOx + (C_BIEN2 + C_BIEN3) / 2#
    xTam(4) = dOx + (C_BIEN3 + C_BIEN4) / 2#

    rongCot(1) = C_BIEN1 - C_BIEN0
    rongCot(2) = C_BIEN2 - C_BIEN1
    rongCot(3) = C_BIEN3 - C_BIEN2
    rongCot(4) = C_BIEN4 - C_BIEN3

    '--- 2.3 Tieu de ---
    If C_GHI_TIEU_DE Then GhiTieuDe dOx, dOy, xTam, rongCot

    '--- 2.4 Tung dong du lieu ---
    For i = 1 To soDinh

        ' tam dong thu i (Y giam dan xuong duoi)
        yTam = dOy + C_YDAU - (CDbl(i) - 0.5) * C_CAODONG

        x1 = ring(lo + i - 1, 0)
        y1 = ring(lo + i - 1, 1)

        ' cot 1: so dinh
        DatChuGiuaO CStr(i), xTam(1), yTam, rongCot(1), C_CAOCHU

        ' cot 2: X(m)   |   cot 3: Y(m)   -> hai TAM X KHAC NHAU
        DatChuGiuaO So2(x1), xTam(2), yTam, rongCot(2), C_CAOCHU
        DatChuGiuaO So2(y1), xTam(3), yTam, rongCot(3), C_CAOCHU

        ' cot 4: chieu dai canh tu dinh i den dinh i+1
        j = lo + i                      ' dinh ke tiep
        If i = soDinh Then j = lo       ' dinh cuoi noi ve dinh dau
        x2 = ring(j, 0)
        y2 = ring(j, 1)
        dCanh = Sqr((x2 - x1) * (x2 - x1) + (y2 - y1) * (y2 - y1))

        If C_CANH_GIUA_HAI_DONG Then
            yCanh = yTam - C_CAODONG / 2#      ' nam tren vach giua 2 dong
        Else
            yCanh = yTam                        ' canh giua dung dong (mac dinh)
        End If
        DatChuGiuaO So2(dCanh), xTam(4), yCanh, rongCot(4), C_CAOCHU

    Next i

    Exit Sub

LoiRoi:
    MsgBox "Loi khi ghi bang toa do: " & Err.Description, _
           vbCritical, "Bang toa do"
End Sub


'==================================================================
' PHAN 3 - TIEU DE BANG
'==================================================================
Private Sub GhiTieuDe(ByVal dOx As Double, ByVal dOy As Double, _
                      xTam() As Double, rongCot() As Double)

    Dim yTD2 As Double, yTD1 As Double
    Dim xTamXY As Double, rongXY As Double
    Dim s1 As String, s2 As String

    ' tam hai dong tieu de
    yTD2 = dOy + C_YDAU + C_CAO_TD2 / 2#
    yTD1 = dOy + C_YDAU + C_CAO_TD2 + C_CAO_TD1 / 2#

    ' "Toa do dinh thua" nam GIUA hai cot X va Y  (khong lan sang cot canh)
    xTamXY = (xTam(2) + xTam(3)) / 2#
    rongXY = rongCot(2) + rongCot(3)

    If C_CO_DAU Then
        s1 = "To" & ChrW(&HE1) & ChrW(&H1EA1) & " " & ChrW(&H111) & _
             ChrW(&HF4) & ChrW(&H323) & "..."      ' de trong, xem ghi chu duoi
        s1 = "Toa do dinh thua"
    Else
        s1 = "Toa do dinh thua"
    End If

    DatChuGiuaO s1, xTamXY, yTD1, rongXY, C_CAOCHU_TD
    DatChuGiuaO "X(m)", xTam(2), yTD2, rongCot(2), C_CAOCHU_TD
    DatChuGiuaO "Y(m)", xTam(3), yTD2, rongCot(3), C_CAOCHU_TD

    ' cot canh: tieu de 2 dong, dat trong pham vi RIENG cua cot 4
    ' -> het de vao chu "Toa do dinh thua"
    s2 = "Kich thuoc canh"
    DatChuGiuaO s2, xTam(4), yTD1 + C_CAOCHU_TD * 0.35, rongCot(4), C_CAOCHU_TD
    DatChuGiuaO "(m)", xTam(4), yTD1 - C_CAOCHU_TD * 0.9, rongCot(4), C_CAOCHU_TD

End Sub


'==================================================================
' PHAN 4 - DAT CHU CANH GIUA O (co tu dong thu nho cho vua cot)
'------------------------------------------------------------------
' Neu du an ban da co ham dat chu rieng, co the thay ruot ham nay
' bang ham do - mien la giu dung 2 diem: CenterCenter va tam o.
'==================================================================
Private Sub DatChuGiuaO(ByVal s As String, ByVal xTam As Double, _
                        ByVal yTam As Double, ByVal rongO As Double, _
                        ByVal caoChu As Double)

    Dim oT As TextElement
    Dim pt As Point3d
    Dim ts As TextStyle
    Dim cao As Double, rongChu As Double

    If Len(Trim$(s)) = 0 Then Exit Sub

    '--- tu dong thu nho neu chuoi rong hon o (chan tuyet doi viec de chu) ---
    cao = caoChu
    rongChu = Len(s) * cao * C_TILE_RONG
    If rongChu > rongO * 0.92 Then
        cao = cao * (rongO * 0.92) / rongChu
    End If

    Set ts = ActiveSettings.TextStyle
    ts.Height = cao
    ts.Width = cao * 0.9
    ts.Justification = msdTextJustificationCenterCenter
    ActiveSettings.TextStyle = ts

    pt.x = xTam
    pt.y = yTam
    pt.Z = 0#

    Set oT = CreateTextElement1(Nothing, s, pt, Matrix3dIdentity)
    Set oT.Level = LayLevel(C_LEVEL)
    ActiveModelReference.AddElement oT

End Sub

Private Function LayLevel(ByVal SoLevel As Long) As Level
    On Error Resume Next
    Set LayLevel = ActiveDesignFile.Levels(SoLevel)
    If LayLevel Is Nothing Then Set LayLevel = ActiveSettings.Level
    On Error GoTo 0
End Function

' So thuc -> chuoi 2 so le, dau thap phan la DAU PHAY (kieu VN)
Private Function So2(ByVal v As Double) As String
    Dim s As String
    s = Format$(v, "0.00")
    So2 = Replace(s, ".", ",")
End Function


'==================================================================
' PHAN 5 - SUB TEST (chay rieng de can hinh hoc bang cho nhanh)
'------------------------------------------------------------------
' Chay Sub nay tren to .dgn DA CHEN KHUNG MAU. No ghi 4 dinh gia
' vao bang -> xem co dung o hay khong, roi sua lai cac hang so
' PHAN 1. Khong can chay ca quy trinh trich luc.
'
' Sua dOx, dOy thanh toa do goc chen khung that cua to dang mo.
'==================================================================
Public Sub TestBang8()

    Dim r(0 To 4, 0 To 1) As Double
    Dim dOx As Double, dOy As Double

    dOx = 0#        '<<< SUA: toa do X goc chen khung
    dOy = 0#        '<<< SUA: toa do Y goc chen khung

    ' hinh chu nhat 10 x 20 (giong to test cua ban)
    r(0, 0) = 530725.1: r(0, 1) = 1099628.52
    r(1, 0) = 530733.1: r(1, 1) = 1099621.54
    r(2, 0) = 530746.85: r(2, 1) = 1099603.34
    r(3, 0) = 530738.85: r(3, 1) = 1099610.32
    r(4, 0) = r(0, 0):   r(4, 1) = r(0, 1)      ' dong ring

    GhiBangDinhThua r, dOx, dOy

    MsgBox "Da ghi bang test. Kiem tra chu co nam giua o chua," & vbCrLf & _
           "neu lech thi sua cac hang so PHAN 1 trong modBang8.", _
           vbInformation, "Test bang muc 8"

End Sub

Attribute VB_Name = "modBatMau"
Option Explicit

'============================================================
' modBatMau - Bat mau khung trich luc tu file .dgn dang mo
'   Quet Line/LineString + Text/TextNode -> ghi ra file .txt
'   (dinh dang H/L/T dung cho lenh chen khung).
'   Chay khi dang MO file .dgn mau (vd TrichLucBanDo.dgn).
'============================================================

Private Function s2(ByVal v As Double) As String
    s2 = Trim$(Str$(v))
End Function

Private Function XoaTab(ByVal s As String) As String
    XoaTab = Replace(Replace(Replace(s, vbTab, " "), vbCr, " "), vbLf, " ")
End Function

' La tag (o dien gia tri) hay text co dinh?
'
' Danh sach nay lay DUNG bo TAG cua file mau dang chay
' (TrichLucBanDo_mau.txt). Doi no la doi hanh vi ve, nen dung "cai tien".
'
' Luu y 4 gia tri cuoi: "X(m)", "Y(m)", "B", "2" KHONG phai tag that.
' Chung phai la TAG de modKhungMau KHONG ve chung tu file mau:
'   - "X(m)", "Y(m)"  : GiaTriTag tra "" -> khong ve. Dung vay, vi modBang8
'                       tu ve tieu de bang muc 8 (xem C_BIEN1/C_BIEN2).
'                       De thanh TEXT la bi ve 2 lan, chu de nhau.
'   - "B", "2"        : GiaTriTag co hai Case rieng tra lai chinh no.
Private Function LaTag(ByVal s As String) As Boolean
    Select Case Trim$(s)
        Case "soHieuThua", "toBanDo", "dienTich", "mdsd", "chuSuDung", _
             "tenXa", "tenHuyen", "tenTinh", "gcn", "tinhhinhthaydoiranhgioi", _
             "tttl", "tamXtl", "tamYtl", "cdtl", _
             "X(m)", "Y(m)", "B", "2"
            LaTag = True
        Case Else
            LaTag = False
    End Select
End Function

' Chieu cao chu tu bounding box cua text
Private Function CaoText(ByVal el As Element) As Double
    Dim r As Range3d
    On Error Resume Next
    r = el.Range
    CaoText = r.High.y - r.Low.y
    On Error GoTo 0
    If CaoText <= 0 Then CaoText = 1
End Function


Public Sub DC_BatMauTrichLuc()
    Dim path As String
    path = InputBox("Ghi file mau (.txt) ra dau:", "Bat mau trich luc", _
                    "C:\DiaChinhVL\MauMoi_mau.txt")
    If path = "" Then Exit Sub

    Dim st As Object
    On Error Resume Next
    Set st = CreateObject("ADODB.Stream")
    On Error GoTo 0
    If st Is Nothing Then MsgBox "Khong tao duoc file.", vbExclamation: Exit Sub
    st.Type = 2: st.Charset = "utf-8": st.Open

    ' Quet
    Dim esc As ElementScanCriteria
    Set esc = New ElementScanCriteria
    esc.ExcludeAllTypes
    esc.IncludeType msdElementTypeLine
    esc.IncludeType msdElementTypeLineString
    esc.IncludeType msdElementTypeText
    esc.IncludeType msdElementTypeTextNode

    Dim ee As ElementEnumerator
    Set ee = ActiveModelReference.Scan(esc)

    Dim minX As Double, minY As Double, maxX As Double, maxY As Double
    Dim first As Boolean: first = True
    Dim nL As Long, nt As Long
    Dim el As Element, ln As String, i As Long
    Dim body As String
    body = ""

    Do While ee.MoveNext
        Set el = ee.Current
        Select Case el.Type
            Case msdElementTypeLine, msdElementTypeLineString
                Dim pts() As Point3d, okV As Boolean
                On Error Resume Next
                Err.Clear
                pts = el.AsLineElement.GetVertices()
                okV = (Err.Number = 0)
                On Error GoTo 0
                ' SUA: GetVertices that bai -> bo qua han, khong dung pts cua vong truoc
                If okV Then
                    ln = "L" & vbTab & el.Level.Number
                    For i = LBound(pts) To UBound(pts)
                        ln = ln & vbTab & s2(pts(i).x) & vbTab & s2(pts(i).y)
                        first = CapNhatBBox(pts(i).x, pts(i).y, first, minX, minY, maxX, maxY)
                    Next i
                    body = body & ln & vbLf
                    nL = nL + 1
                End If

            Case msdElementTypeText
                Dim oT As TextElement, o As Point3d, s As String, cao As Double
                Set oT = el
                o = oT.Origin: s = Trim$(oT.Text): cao = CaoText(el)
                body = body & GhiText(el.Level.Number, s, cao, o.x, o.y)
                first = CapNhatBBox(o.x, o.y, first, minX, minY, maxX, maxY)
                nt = nt + 1

            Case msdElementTypeTextNode
                Dim oNode As TextNodeElement, subs As ElementEnumerator
                Set oNode = el
                Set subs = oNode.GetSubElements
                Do While subs.MoveNext
                    If subs.Current.Type = msdElementTypeText Then
                        Dim oc As TextElement, oc2 As Point3d, sc As String, cc As Double
                        Set oc = subs.Current
                        oc2 = oc.Origin: sc = Trim$(oc.Text): cc = CaoText(subs.Current)
                        If Len(sc) > 0 Then
                            body = body & GhiText(el.Level.Number, sc, cc, oc2.x, oc2.y)
                            first = CapNhatBBox(oc2.x, oc2.y, first, minX, minY, maxX, maxY)
                            nt = nt + 1
                        End If
                    End If
                Loop
        End Select
    Loop

    ' Dong dau H (uor_m=1)
    st.WriteText "H" & vbTab & "1" & vbTab & s2(minX) & vbTab & s2(minY) & vbTab & _
                 s2(maxX) & vbTab & s2(maxY) & vbLf
    st.WriteText body

    On Error Resume Next
    Err.Clear                      ' SUA: khong xoa thi Err con ban tu CaoText/GetVertices
    st.SaveToFile path, 2
    Dim ok As Boolean: ok = (Err.Number = 0)
    st.Close
    On Error GoTo 0

    MsgBox "Bat mau xong: " & nL & " line, " & nt & " text." & vbCrLf & _
           IIf(ok, "Da ghi: " & path, "KHONG ghi duoc: " & path) & vbCrLf & vbCrLf & _
           "Trong hop thoai Trich luc, tro o 'File mau' toi file nay.", _
           vbInformation, "Bat mau trich luc"
End Sub

Private Function GhiText(ByVal lv As Long, ByVal s As String, ByVal cao As Double, _
                         ByVal x As Double, ByVal y As Double) As String
    Dim kind As String
    If LaTag(s) Then kind = "TAG" Else kind = "TEXT"
    GhiText = "T" & vbTab & lv & vbTab & kind & vbTab & s2(cao) & vbTab & _
              s2(x) & vbTab & s2(y) & vbTab & XoaTab(s) & vbLf
End Function

Private Function CapNhatBBox(ByVal x As Double, ByVal y As Double, ByVal first As Boolean, _
                             ByRef minX As Double, ByRef minY As Double, _
                             ByRef maxX As Double, ByRef maxY As Double) As Boolean
    If first Then
        minX = x: maxX = x: minY = y: maxY = y
        CapNhatBBox = False
    Else
        If x < minX Then minX = x
        If x > maxX Then maxX = x
        If y < minY Then minY = y
        If y > maxY Then maxY = y
        CapNhatBBox = False
    End If
End Function

Attribute VB_Name = "modBienTap"
'============================================================
' modBienTap - Menu Bien tap kieu LandMap
'   Bang "Quy dinh lop": C:\DiaChinhVL\QuyDinhLop.txt (UTF-8, sua bang Notepad)
'     Nhom|Ma|Ten hien thi|Loai|Level|Mau|KieuNet|LucNet|CoChu(mm giay)
'     Loai: L = noi duong (Place SmartLine), T = ghi chu (Place Text), K = ky hieu (chua lam -> mo)
'   Chon muc -> dat level/mau/net (va co chu theo ty le ban do) -> mo lenh ve.
'   Ty le ban do: ini TYLE_BD (dung tinh co chu ghi chu).
'============================================================
Option Explicit

Public Const BT_FILE As String = "C:\DiaChinhVL\QuyDinhLop.txt"

Private mFont As Object

Private Function tieuDe() As String
    tieuDe = "Bi" & ChrW(234) & "n t" & ChrW(7853) & "p"
End Function

'------------------------------------------------------------ TY LE BAN DO
Public Function DC_TyLeBD() As Long
    DC_TyLeBD = CLng(val(DC_DocCauHinh("TYLE_BD", "1000")))
    If DC_TyLeBD <= 0 Then DC_TyLeBD = 1000
End Function

Public Sub DC_DatTyLeBD(ByVal tL As Long)
    If tL <= 0 Then Exit Sub
    DC_GhiCauHinh "TYLE_BD", CStr(tL)
    On Error Resume Next
    ShowStatus "Ty le ban do 1:" & tL
End Sub

'------------------------------------------------------------ BANG QUY DINH LOP
' Tra ve Collection, moi phan tu = mang String(0..8)
Public Function BT_DocBang() As Collection
    Dim kq As New Collection, txt As String, Dong() As String, i As Long, p() As String, j As Long
    Set BT_DocBang = kq
    If Len(Dir$(BT_FILE)) = 0 Then GhiBangMacDinh
    txt = DocUtf8(BT_FILE)
    If Len(txt) = 0 Then txt = BangMacDinh()
    Dong = Split(Replace(txt, vbCr, ""), vbLf)
    For i = 0 To UBound(Dong)
        If Len(Trim$(Dong(i))) > 0 And Left$(Trim$(Dong(i)), 1) <> "#" Then
            p = Split(Dong(i), "|")
            If UBound(p) >= 3 Then
                ReDim Preserve p(0 To 8)
                For j = 0 To 8
                    p(j) = Trim$(p(j))
                Next j
                kq.Add p
            End If
        End If
    Next i
End Function

Private Function TimMa(ByVal ma As String) As Variant
    Dim dS As Collection, i As Long
    Set dS = BT_DocBang()
    For i = 1 To dS.Count
        If StrComp(dS.Item(i)(1), ma, vbTextCompare) = 0 Then TimMa = dS.Item(i): Exit Function
    Next i
    TimMa = Empty
End Function

' Mo file quy dinh lop bang Notepad (tao mac dinh neu chua co)
Public Sub DC_QuyDinhLop()
    If Len(Dir$(BT_FILE)) = 0 Then GhiBangMacDinh
    If Len(Dir$(BT_FILE)) = 0 Then
        DC_ThongBao "Kh" & ChrW(244) & "ng t" & ChrW(7841) & "o " & ChrW(273) & ChrW(432) & ChrW(7907) & "c file " & BT_FILE, tieuDe, vbExclamation
        Exit Sub
    End If
    Shell "notepad.exe """ & BT_FILE & """", vbNormalFocus
    DC_ThongBao "S" & ChrW(7917) & "a level / m" & ChrW(224) & "u / ki" & ChrW(7875) & "u n" & ChrW(233) & "t / l" & ChrW(7921) & "c n" & ChrW(233) & "t / c" & ChrW(7905) & " ch" & ChrW(7919) & " trong file r" & ChrW(7891) & "i l" & ChrW(432) & "u l" & ChrW(7841) & "i." & vbCrLf & _
                "Menu Bi" & ChrW(234) & "n t" & ChrW(7853) & "p d" & ChrW(249) & "ng ngay gi" & ChrW(225) & " tr" & ChrW(7883) & " m" & ChrW(7899) & "i (kh" & ChrW(244) & "ng c" & ChrW(7847) & "n m" & ChrW(7903) & " l" & ChrW(7841) & "i MicroStation)." & vbCrLf & _
                "C" & ChrW(7905) & " ch" & ChrW(7919) & " ghi theo mm tr" & ChrW(234) & "n gi" & ChrW(7845) & "y; chi" & ChrW(7873) & "u cao th" & ChrW(7853) & "t = mm x t" & ChrW(7927) & " l" & ChrW(7879) & " / 1000.", tieuDe
End Sub

'------------------------------------------------------------ CHAY 1 MUC
Public Sub DC_BienTap(ByVal ma As String)
    Dim r As Variant, lv As Level, cao As Double, f As Object
    r = TimMa(ma)
    If IsEmpty(r) Then
        DC_ThongBao "Ch" & ChrW(432) & "a c" & ChrW(243) & " m" & ChrW(7909) & "c '" & ma & "' trong " & BT_FILE, tieuDe, vbExclamation
        Exit Sub
    End If
    On Error Resume Next
    If val(r(4)) > 0 Then
        Set lv = DC_LevelTheoSo(CLng(val(r(4))))
        If Not lv Is Nothing Then Set ActiveSettings.Level = lv
    End If
    ActiveSettings.color = CLng(val(r(5)))
    ActiveSettings.LineWeight = CLng(val(r(7)))
    CadInputQueue.SendKeyin "lc=" & CLng(val(r(6)))
    Select Case UCase$(r(3))
    Case "L"
        CadInputQueue.SendKeyin "place smartline"
        ShowPrompt "DiaChinhVL: " & ma
    Case "T"
        cao = val(Replace(r(8), ",", ".")) * DC_TyLeBD() / 1000#
        If cao <= 0 Then cao = 2 * DC_TyLeBD() / 1000#
        ActiveSettings.TextStyle.Height = cao
        ActiveSettings.TextStyle.Width = cao
        Set f = FontVN()
        If Not f Is Nothing Then Set ActiveSettings.TextStyle.Font = f
        CadInputQueue.SendKeyin "place text"
        ShowPrompt "DiaChinhVL: " & ma & " (co chu " & Format$(cao, "0.00") & " m)"
    Case Else
        DC_ThongBao "M" & ChrW(7909) & "c k" & ChrW(253) & " hi" & ChrW(7879) & "u n" & ChrW(224) & "y ch" & ChrW(432) & "a l" & ChrW(224) & "m (c" & ChrW(7847) & "n th" & ChrW(432) & " vi" & ChrW(7879) & "n cell).", tieuDe, vbExclamation
    End Select
End Sub

Private Function FontVN() As Object
    Dim f As Object
    If Not mFont Is Nothing Then Set FontVN = mFont: Exit Function
    On Error Resume Next
    For Each f In ActiveDesignFile.Fonts
        If StrComp(f.Name, DC_FONT_VIET, vbTextCompare) = 0 Then Set mFont = f: Exit For
    Next f
    Set FontVN = mFont
End Function

'------------------------------------------------------------ FILE UTF-8
Private Function DocUtf8(ByVal f As String) As String
    Dim st As Object
    On Error Resume Next
    Set st = CreateObject("ADODB.Stream")
    st.Type = 2: st.Charset = "utf-8": st.Open
    st.LoadFromFile f
    DocUtf8 = st.ReadText(-1)
    st.Close
    If Len(DocUtf8) > 0 Then
        If AscW(Left$(DocUtf8, 1)) = &HFEFF Then DocUtf8 = Mid$(DocUtf8, 2)
    End If
End Function

Private Sub GhiBangMacDinh()
    Dim st As Object
    On Error Resume Next
    If Len(Dir$(DC_THUMUC, vbDirectory)) = 0 Then MkDir DC_THUMUC
    Set st = CreateObject("ADODB.Stream")
    st.Type = 2: st.Charset = "utf-8": st.Open
    st.WriteText BangMacDinh()
    st.SaveToFile BT_FILE, 2
    st.Close
End Sub

' Bang mac dinh (GOI Y - nguoi dung sua theo quy dinh lop cua don vi)
Private Function BangMacDinh() As String
    Dim s As String
    s = "# QUY " & ChrW(272) & ChrW(7882) & "NH L" & ChrW(7898) & "P - DiaChinhVL (s" & ChrW(7917) & "a theo quy " & ChrW(273) & ChrW(7883) & "nh c" & ChrW(7911) & "a " & ChrW(273) & ChrW(417) & "n v" & ChrW(7883) & " r" & ChrW(7891) & "i l" & ChrW(432) & "u UTF-8)" & vbCrLf
    s = s & "# Nh" & ChrW(243) & "m|M" & ChrW(227) & "|T" & ChrW(234) & "n hi" & ChrW(7875) & "n th" & ChrW(7883) & "|Lo" & ChrW(7841) & "i (L=n" & ChrW(7889) & "i " & ChrW(273) & ChrW(432) & ChrW(7901) & "ng, T=ghi ch" & ChrW(250) & ", K=k" & ChrW(253) & " hi" & ChrW(7879) & "u)|Level|M" & ChrW(224) & "u|Ki" & ChrW(7875) & "u n" & ChrW(233) & "t|L" & ChrW(7921) & "c n" & ChrW(233) & "t|C" & ChrW(7905) & " ch" & ChrW(7919) & " mm" & vbCrLf
    s = s & "THUA|TD_RANH|N" & ChrW(7889) & "i ranh gi" & ChrW(7899) & "i th" & ChrW(7917) & "a " & ChrW(273) & ChrW(7845) & "t|L|10|0|0|0|" & vbCrLf
    s = s & "THUA|TD_MEPGT|N" & ChrW(7889) & "i th" & ChrW(7917) & "a tr" & ChrW(249) & "ng m" & ChrW(233) & "p giao th" & ChrW(244) & "ng|L|10|0|0|0|" & vbCrLf
    s = s & "THUA|TD_MEPTV|N" & ChrW(7889) & "i th" & ChrW(7917) & "a tr" & ChrW(249) & "ng m" & ChrW(233) & "p th" & ChrW(7911) & "y v" & ChrW(259) & "n|L|10|0|0|0|" & vbCrLf
    s = s & "THUA|TD_KHEP|N" & ChrW(7889) & "i n" & ChrW(233) & "t th" & ChrW(7917) & "a kh" & ChrW(233) & "p m" & ChrW(432) & ChrW(417) & "ng " & ChrW(273) & ChrW(432) & ChrW(7901) & "ng|L|10|0|2|0|" & vbCrLf
    s = s & "THUA|TD_TRANHCHAP|N" & ChrW(7889) & "i ranh gi" & ChrW(7899) & "i th" & ChrW(7917) & "a " & ChrW(273) & "ang tranh ch" & ChrW(7845) & "p|L|10|3|3|0|" & vbCrLf
    s = s & "NHA|NHA_TUONG|N" & ChrW(7889) & "i t" & ChrW(432) & ChrW(7901) & "ng nh" & ChrW(224) & "|L|14|0|0|0|" & vbCrLf
    s = s & "NHA|NHA_VUONG|N" & ChrW(7889) & "i t" & ChrW(432) & ChrW(7901) & "ng nh" & ChrW(224) & " vu" & ChrW(244) & "ng g" & ChrW(243) & "c|L|14|0|0|0|" & vbCrLf
    s = s & "NHA|NHA_GHICHU|Ghi ch" & ChrW(250) & " t" & ChrW(237) & "nh ch" & ChrW(7845) & "t nh" & ChrW(224) & "|T|15|0|0|0|1.5" & vbCrLf
    s = s & "NHA|NHA_TUONGRIENG|K" & ChrW(237) & " hi" & ChrW(7879) & "u t" & ChrW(432) & ChrW(7901) & "ng ri" & ChrW(234) & "ng|K|14|0|0|0|" & vbCrLf
    s = s & "NHA|NHA_TUONGCHUNG|K" & ChrW(237) & " hi" & ChrW(7879) & "u t" & ChrW(432) & ChrW(7901) & "ng chung|K|14|0|0|0|" & vbCrLf
    s = s & "GT|GT_MEP|N" & ChrW(7889) & "i m" & ChrW(233) & "p " & ChrW(273) & ChrW(432) & ChrW(7901) & "ng|L|23|0|0|0|" & vbCrLf
    s = s & "GT|GT_NHUA|N" & ChrW(7889) & "i m" & ChrW(233) & "p nh" & ChrW(7921) & "a|L|24|0|0|0|" & vbCrLf
    s = s & "GT|GT_1NET|N" & ChrW(7889) & "i " & ChrW(273) & ChrW(432) & ChrW(7901) & "ng m" & ChrW(7897) & "t n" & ChrW(233) & "t|L|25|0|0|0|" & vbCrLf
    s = s & "GT|GT_RAY|N" & ChrW(7889) & "i " & ChrW(273) & ChrW(432) & ChrW(7901) & "ng ray|L|27|0|0|0|" & vbCrLf
    s = s & "GT|GT_CHIGIOIRAY|N" & ChrW(7889) & "i ch" & ChrW(7881) & " gi" & ChrW(7899) & "i " & ChrW(273) & ChrW(432) & ChrW(7901) & "ng ray|L|27|0|2|0|" & vbCrLf
    s = s & "GT|GT_RAY1NET|N" & ChrW(7889) & "i " & ChrW(273) & ChrW(432) & ChrW(7901) & "ng ray m" & ChrW(7897) & "t n" & ChrW(233) & "t|L|27|0|0|0|" & vbCrLf
    s = s & "GT|GT_TRONGTHUA|N" & ChrW(7889) & "i " & ChrW(273) & ChrW(432) & ChrW(7901) & "ng trong th" & ChrW(7917) & "a|L|23|0|2|0|" & vbCrLf
    s = s & "GT|GT_PHANCACH|N" & ChrW(7889) & "i " & ChrW(273) & ChrW(432) & ChrW(7901) & "ng ph" & ChrW(226) & "n c" & ChrW(225) & "ch ch" & ChrW(7845) & "t li" & ChrW(7879) & "u r" & ChrW(7843) & "i m" & ChrW(7863) & "t|L|24|0|3|0|" & vbCrLf
    s = s & "GT|GT_GC_LIENXA|Ghi ch" & ChrW(250) & " " & ChrW(273) & ChrW(432) & ChrW(7901) & "ng li" & ChrW(234) & "n x" & ChrW(227) & ", li" & ChrW(234) & "n th" & ChrW(244) & "n|T|26|0|0|0|2.0" & vbCrLf
    s = s & "GT|GT_GC_QUOCLO|Ghi ch" & ChrW(250) & " " & ChrW(273) & ChrW(432) & ChrW(7901) & "ng qu" & ChrW(7889) & "c l" & ChrW(7897) & " + t" & ChrW(237) & "nh ch" & ChrW(7845) & "t|T|26|0|0|0|2.5" & vbCrLf
    s = s & "GT|GT_GC_DAILO|Ghi ch" & ChrW(250) & " t" & ChrW(234) & "n " & ChrW(273) & ChrW(432) & ChrW(7901) & "ng ph" & ChrW(7889) & " (" & ChrW(273) & ChrW(7841) & "i l" & ChrW(7897) & ")|T|26|0|0|0|3.0" & vbCrLf
    s = s & "GT|GT_GC_PHOVUA|Ghi ch" & ChrW(250) & " t" & ChrW(234) & "n " & ChrW(273) & ChrW(432) & ChrW(7901) & "ng ph" & ChrW(7889) & " (ph" & ChrW(7889) & " v" & ChrW(7915) & "a)|T|26|0|0|0|2.5" & vbCrLf
    s = s & "GT|GT_GC_PHONHO|Ghi ch" & ChrW(250) & " t" & ChrW(234) & "n " & ChrW(273) & ChrW(432) & ChrW(7901) & "ng ph" & ChrW(7889) & " (ph" & ChrW(7889) & " nh" & ChrW(7887) & ", h" & ChrW(7867) & "m)|T|26|0|0|0|2.0" & vbCrLf
    s = s & "GT|GT_GC_DORONG|Ghi ch" & ChrW(250) & " " & ChrW(273) & ChrW(7897) & " r" & ChrW(7897) & "ng trung b" & ChrW(236) & "nh c" & ChrW(7911) & "a " & ChrW(273) & ChrW(432) & ChrW(7901) & "ng|T|26|0|0|0|1.75" & vbCrLf
    s = s & "GT|GT_MUITEN|M" & ChrW(361) & "i t" & ChrW(234) & "n ch" & ChrW(7881) & " ghi ch" & ChrW(250) & " " & ChrW(273) & ChrW(7897) & " r" & ChrW(7897) & "ng " & ChrW(273) & ChrW(432) & ChrW(7901) & "ng|K|26|0|0|0|" & vbCrLf
    s = s & "GT|GT_CAU2NET|C" & ChrW(7847) & "u 2 n" & ChrW(233) & "t (c" & ChrW(7847) & "u theo t" & ChrW(7927) & " l" & ChrW(7879) & ")|K|28|0|0|0|" & vbCrLf
    s = s & "GT|GT_CAUPHI|C" & ChrW(7847) & "u phi t" & ChrW(7927) & " l" & ChrW(7879) & "|K|28|0|0|0|" & vbCrLf
    s = s & "GT|GT_CAUNUA|C" & ChrW(7847) & "u n" & ChrW(7917) & "a theo t" & ChrW(7927) & " l" & ChrW(7879) & "|K|28|0|0|0|" & vbCrLf
    s = s & "TV|TV_BONUOC|N" & ChrW(7889) & "i " & ChrW(273) & ChrW(432) & ChrW(7901) & "ng b" & ChrW(7901) & " n" & ChrW(432) & ChrW(7899) & "c|L|32|1|0|0|" & vbCrLf
    s = s & "TV|TV_MEPNUOC|N" & ChrW(7889) & "i " & ChrW(273) & ChrW(432) & ChrW(7901) & "ng m" & ChrW(233) & "p n" & ChrW(432) & ChrW(7899) & "c|L|32|1|0|0|" & vbCrLf
    s = s & "TV|TV_KENH|N" & ChrW(7889) & "i k" & ChrW(234) & "nh m" & ChrW(432) & ChrW(417) & "ng r" & ChrW(227) & "nh|L|33|1|0|0|" & vbCrLf
    s = s & "TV|TV_1NET|N" & ChrW(7889) & "i th" & ChrW(7911) & "y v" & ChrW(259) & "n m" & ChrW(7897) & "t n" & ChrW(233) & "t|L|34|1|0|0|" & vbCrLf
    s = s & "TV|TV_CHANDE|N" & ChrW(7889) & "i " & ChrW(273) & ChrW(432) & ChrW(7901) & "ng ch" & ChrW(226) & "n " & ChrW(273) & ChrW(234) & "|L|36|0|0|0|" & vbCrLf
    s = s & "TV|TV_MATDE|N" & ChrW(7889) & "i " & ChrW(273) & ChrW(432) & ChrW(7901) & "ng m" & ChrW(7863) & "t " & ChrW(273) & ChrW(234) & "|L|36|0|0|0|" & vbCrLf
    s = s & "TV|TV_DE1NET|N" & ChrW(7889) & "i " & ChrW(273) & ChrW(234) & " m" & ChrW(7897) & "t n" & ChrW(233) & "t|L|36|0|0|0|" & vbCrLf
    s = s & "TV|TV_TRONGTHUA|N" & ChrW(7889) & "i th" & ChrW(7911) & "y v" & ChrW(259) & "n trong th" & ChrW(7917) & "a|L|32|1|2|0|" & vbCrLf
    s = s & "TV|TV_GC_SONGLON|Ghi ch" & ChrW(250) & " t" & ChrW(234) & "n s" & ChrW(244) & "ng l" & ChrW(7899) & "n|T|35|1|0|0|4.0" & vbCrLf
    s = s & "TV|TV_GC_SONGVUA|Ghi ch" & ChrW(250) & " t" & ChrW(234) & "n s" & ChrW(244) & "ng v" & ChrW(7915) & "a|T|35|1|0|0|3.0" & vbCrLf
    s = s & "TV|TV_GC_SONGNHO|Ghi ch" & ChrW(250) & " t" & ChrW(234) & "n s" & ChrW(244) & "ng nh" & ChrW(7887) & "|T|35|1|0|0|2.5" & vbCrLf
    s = s & "TV|TV_GC_SUOI|Ghi ch" & ChrW(250) & " t" & ChrW(234) & "n su" & ChrW(7889) & "i, ao, h" & ChrW(7891) & "|T|35|1|0|0|2.0" & vbCrLf
    s = s & "TV|TV_GC_RACH|Ghi ch" & ChrW(250) & " su" & ChrW(7889) & "i nh" & ChrW(7887) & ", r" & ChrW(227) & "nh, m" & ChrW(432) & ChrW(417) & "ng|T|35|1|0|0|1.75" & vbCrLf
    s = s & "TV|TV_MUITENRONG|M" & ChrW(361) & "i t" & ChrW(234) & "n ch" & ChrW(7881) & " " & ChrW(273) & ChrW(7897) & " r" & ChrW(7897) & "ng trung b" & ChrW(236) & "nh|K|35|1|0|0|" & vbCrLf
    s = s & "TV|TV_MUITENCHAY|M" & ChrW(361) & "i t" & ChrW(234) & "n h" & ChrW(432) & ChrW(7899) & "ng n" & ChrW(432) & ChrW(7899) & "c ch" & ChrW(7843) & "y|K|35|1|0|0|" & vbCrLf
    s = s & "TV|TV_CONGDAP|C" & ChrW(7889) & "ng " & ChrW(273) & ChrW(7853) & "p theo t" & ChrW(7927) & " l" & ChrW(7879) & "|K|37|0|0|0|" & vbCrLf
    s = s & "TV|TV_CONGDAPPHI|C" & ChrW(7889) & "ng " & ChrW(273) & ChrW(7853) & "p phi t" & ChrW(7927) & " l" & ChrW(7879) & "|K|37|0|0|0|" & vbCrLf
    s = s & "TV|TV_CONGTHOAT|C" & ChrW(7889) & "ng tho" & ChrW(225) & "t n" & ChrW(432) & ChrW(7899) & "c|K|37|0|0|0|" & vbCrLf
    s = s & "DG|DG_QG_XD|Bi" & ChrW(234) & "n gi" & ChrW(7899) & "i qu" & ChrW(7889) & "c gia x" & ChrW(225) & "c " & ChrW(273) & ChrW(7883) & "nh|L|41|0|0|0|" & vbCrLf
    s = s & "DG|DG_QG_CXD|Bi" & ChrW(234) & "n gi" & ChrW(7899) & "i qu" & ChrW(7889) & "c gia ch" & ChrW(432) & "a x" & ChrW(225) & "c " & ChrW(273) & ChrW(7883) & "nh|L|41|0|2|0|" & vbCrLf
    s = s & "DG|DG_QG_MOC|M" & ChrW(7889) & "c bi" & ChrW(234) & "n gi" & ChrW(7899) & "i qu" & ChrW(7889) & "c gia|K|41|0|0|0|" & vbCrLf
    s = s & "DG|DG_QG_GCMOC|Ghi ch" & ChrW(250) & " s" & ChrW(7889) & " hi" & ChrW(7879) & "u m" & ChrW(7889) & "c qu" & ChrW(7889) & "c gia|T|41|0|0|0|2.0" & vbCrLf
    s = s & "DG|DG_TINH_XD|" & ChrW(272) & ChrW(7883) & "a gi" & ChrW(7899) & "i t" & ChrW(7881) & "nh x" & ChrW(225) & "c " & ChrW(273) & ChrW(7883) & "nh|L|42|0|0|0|" & vbCrLf
    s = s & "DG|DG_TINH_CXD|" & ChrW(272) & ChrW(7883) & "a gi" & ChrW(7899) & "i t" & ChrW(7881) & "nh ch" & ChrW(432) & "a x" & ChrW(225) & "c " & ChrW(273) & ChrW(7883) & "nh|L|42|0|2|0|" & vbCrLf
    s = s & "DG|DG_TINH_MOC|M" & ChrW(7889) & "c " & ChrW(273) & ChrW(7883) & "a gi" & ChrW(7899) & "i t" & ChrW(7881) & "nh|K|42|0|0|0|" & vbCrLf
    s = s & "DG|DG_TINH_GCMOC|Ghi ch" & ChrW(250) & " s" & ChrW(7889) & " hi" & ChrW(7879) & "u m" & ChrW(7889) & "c (t" & ChrW(7881) & "nh)|T|42|0|0|0|1.75" & vbCrLf
    s = s & "DG|DG_TINH_TEN|Ghi ch" & ChrW(250) & " t" & ChrW(234) & "n t" & ChrW(7881) & "nh " & ChrW(273) & ChrW(7847) & "u " & ChrW(273) & ChrW(7883) & "a gi" & ChrW(7899) & "i|T|42|0|0|0|3.0" & vbCrLf
    s = s & "DG|DG_TINH_TENNGOAI|Ghi ch" & ChrW(250) & " t" & ChrW(234) & "n t" & ChrW(7881) & "nh ti" & ChrW(7871) & "p gi" & ChrW(225) & "p ngo" & ChrW(224) & "i " & ChrW(273) & ChrW(7883) & "a gi" & ChrW(7899) & "i|T|42|0|0|0|3.0" & vbCrLf
    s = s & "DG|DG_HUYEN_XD|" & ChrW(272) & ChrW(7883) & "a gi" & ChrW(7899) & "i huy" & ChrW(7879) & "n x" & ChrW(225) & "c " & ChrW(273) & ChrW(7883) & "nh|L|43|0|0|0|" & vbCrLf
    s = s & "DG|DG_HUYEN_CXD|" & ChrW(272) & ChrW(7883) & "a gi" & ChrW(7899) & "i huy" & ChrW(7879) & "n ch" & ChrW(432) & "a x" & ChrW(225) & "c " & ChrW(273) & ChrW(7883) & "nh|L|43|0|2|0|" & vbCrLf
    s = s & "DG|DG_HUYEN_MOC|M" & ChrW(7889) & "c " & ChrW(273) & ChrW(7883) & "a gi" & ChrW(7899) & "i huy" & ChrW(7879) & "n|K|43|0|0|0|" & vbCrLf
    s = s & "DG|DG_HUYEN_GCMOC|Ghi ch" & ChrW(250) & " s" & ChrW(7889) & " hi" & ChrW(7879) & "u m" & ChrW(7889) & "c (huy" & ChrW(7879) & "n)|T|43|0|0|0|1.75" & vbCrLf
    s = s & "DG|DG_HUYEN_TEN|Ghi ch" & ChrW(250) & " t" & ChrW(234) & "n huy" & ChrW(7879) & "n " & ChrW(273) & ChrW(7847) & "u " & ChrW(273) & ChrW(7883) & "a gi" & ChrW(7899) & "i|T|43|0|0|0|2.5" & vbCrLf
    s = s & "DG|DG_HUYEN_TENNGOAI|Ghi ch" & ChrW(250) & " t" & ChrW(234) & "n huy" & ChrW(7879) & "n ti" & ChrW(7871) & "p gi" & ChrW(225) & "p ngo" & ChrW(224) & "i " & ChrW(273) & ChrW(7883) & "a gi" & ChrW(7899) & "i|T|43|0|0|0|2.5" & vbCrLf
    s = s & "DG|DG_XA_XD|" & ChrW(272) & ChrW(7883) & "a gi" & ChrW(7899) & "i x" & ChrW(227) & " x" & ChrW(225) & "c " & ChrW(273) & ChrW(7883) & "nh|L|44|0|0|0|" & vbCrLf
    s = s & "DG|DG_XA_CXD|" & ChrW(272) & ChrW(7883) & "a gi" & ChrW(7899) & "i x" & ChrW(227) & " ch" & ChrW(432) & "a x" & ChrW(225) & "c " & ChrW(273) & ChrW(7883) & "nh|L|44|0|2|0|" & vbCrLf
    s = s & "DG|DG_XA_MOC|M" & ChrW(7889) & "c " & ChrW(273) & ChrW(7883) & "a gi" & ChrW(7899) & "i x" & ChrW(227) & "|K|44|0|0|0|" & vbCrLf
    s = s & "DG|DG_XA_GCMOC|Ghi ch" & ChrW(250) & " s" & ChrW(7889) & " hi" & ChrW(7879) & "u m" & ChrW(7889) & "c (x" & ChrW(227) & ")|T|44|0|0|0|1.75" & vbCrLf
    s = s & "DG|DG_XA_TEN|Ghi ch" & ChrW(250) & " t" & ChrW(234) & "n x" & ChrW(227) & " " & ChrW(273) & ChrW(7847) & "u " & ChrW(273) & ChrW(7883) & "a gi" & ChrW(7899) & "i|T|44|0|0|0|2.0" & vbCrLf
    s = s & "DG|DG_XA_TENNGOAI|Ghi ch" & ChrW(250) & " t" & ChrW(234) & "n x" & ChrW(227) & " ti" & ChrW(7871) & "p gi" & ChrW(225) & "p ngo" & ChrW(224) & "i " & ChrW(273) & ChrW(7883) & "a gi" & ChrW(7899) & "i|T|44|0|0|0|2.0" & vbCrLf
    s = s & "DG|DG_DIADANH|Ghi ch" & ChrW(250) & " t" & ChrW(234) & "n " & ChrW(273) & ChrW(7883) & "a danh, c" & ChrW(7909) & "m d" & ChrW(226) & "n c" & ChrW(432) & "|T|45|0|0|0|2.5" & vbCrLf
    BangMacDinh = s
End Function

Attribute VB_Name = "modCSDL"
Option Explicit

'============================================================
' modCSDL - Co so du lieu tho ban do (giong .dvl cua Python)
' Luu/mo toan bo thua (hinh hoc + thuoc tinh) ra 1 file text.
' Quy trinh: (1) Tao CSDL (ghep vung -> luu)
'            (2) Xem bang du lieu (mo CSDL -> Excel)
'            (3) Gan nhan doc tu CSDL (buoc sau)
'
' Dinh dang file (UTF-8, tab):
'   V  cx  cy  dt  soThua  soTo  loaiDat  tenChu  diaChi
'   R  x0 y0 x1 y1 ...        (ring ngoai, vong kin)
'   D  x0 y0 ...              (moi lo dao 1 dong)
'============================================================

' So -> chuoi dau "." (khong phu thuoc locale)
Private Function s2(ByVal v As Double) As String
    s2 = Trim$(Str$(v))
End Function

Private Function XoaTab(ByVal s As String) As String
    XoaTab = Replace(Replace(Replace(s, vbTab, " "), vbCr, " "), vbLf, " ")
End Function


'============================================================
' LUU CSDL
'============================================================
Public Function LuuCSDL(ByVal vungs As Collection, ByVal path As String) As Boolean
    LuuCSDL = False
    Dim st As Object
    On Error Resume Next
    Set st = CreateObject("ADODB.Stream")
    On Error GoTo 0
    If st Is Nothing Then Exit Function
    st.Type = 2: st.Charset = "utf-8": st.Open

    Dim i As Long, v As clsVung, ring() As Double, n As Long, j As Long
    Dim ln As String, k As Long, dr() As Double, m As Long
    For i = 1 To vungs.Count
        Set v = vungs.Item(i)
        st.WriteText "V" & vbTab & s2(v.cx) & vbTab & s2(v.cy) & vbTab & s2(v.dt) & vbTab & _
                     XoaTab(v.soThua) & vbTab & XoaTab(v.SoTo) & vbTab & XoaTab(v.loaiDat) & vbTab & _
                     XoaTab(v.TenChu) & vbTab & XoaTab(v.DiaChi) & vbCrLf
        If v.HasRing Then
            ring = v.ring
            n = UBound(ring, 1)
            ln = "R"
            For j = 0 To n
                ln = ln & vbTab & s2(ring(j, 0)) & vbTab & s2(ring(j, 1))
            Next j
            st.WriteText ln & vbCrLf
        End If
        For k = 1 To v.dao.Count
            dr = v.dao.Item(k)
            m = UBound(dr, 1)
            ln = "D"
            For j = 0 To m
                ln = ln & vbTab & s2(dr(j, 0)) & vbTab & s2(dr(j, 1))
            Next j
            st.WriteText ln & vbCrLf
        Next k
    Next i

    On Error Resume Next
    st.SaveToFile path, 2
    If Err.Number = 0 Then LuuCSDL = True
    st.Close
    On Error GoTo 0
End Function


'============================================================
' MO CSDL -> Collection clsVung
'============================================================
Public Function MoCSDL(ByVal path As String) As Collection
    Dim coll As New Collection
    Dim st As Object
    On Error Resume Next
    Set st = CreateObject("ADODB.Stream")
    On Error GoTo 0
    If st Is Nothing Then Set MoCSDL = coll: Exit Function
    st.Type = 2: st.Charset = "utf-8": st.Open
    On Error Resume Next
    st.LoadFromFile path
    If Err.Number <> 0 Then st.Close: Set MoCSDL = coll: Exit Function
    On Error GoTo 0
    Dim txt As String
    txt = st.ReadText(-1)
    st.Close

    Dim raw() As String, i As Long, parts() As String
    raw = Split(txt, vbLf)
    Dim v As clsVung
    Set v = Nothing
    Dim pairs As Long, j As Long
    Dim ring() As Double
    For i = LBound(raw) To UBound(raw)
        raw(i) = Replace(raw(i), vbCr, "")      ' file CRLF -> bo CR (cot Dia chi bi dau CR)
        If Len(Trim$(raw(i))) = 0 Then GoTo tt
        parts = Split(raw(i), vbTab)
        Select Case parts(0)
            Case "V"
                If Not v Is Nothing Then coll.Add v
                Set v = New clsVung
                v.cx = val(parts(1)): v.cy = val(parts(2)): v.dt = val(parts(3))
                If UBound(parts) >= 4 Then v.soThua = parts(4)
                If UBound(parts) >= 5 Then v.SoTo = parts(5)
                If UBound(parts) >= 6 Then v.loaiDat = parts(6)
                If UBound(parts) >= 7 Then v.TenChu = parts(7)
                If UBound(parts) >= 8 Then v.DiaChi = parts(8)
            Case "R"
                If Not v Is Nothing Then
                    pairs = UBound(parts) \ 2
                    ReDim ring(0 To pairs - 1, 0 To 1)
                    For j = 0 To pairs - 1
                        ring(j, 0) = val(parts(1 + 2 * j))
                        ring(j, 1) = val(parts(2 + 2 * j))
                    Next j
                    v.ring = ring
                    v.HasRing = True
                End If
            Case "D"
                If Not v Is Nothing Then
                    pairs = UBound(parts) \ 2
                    ReDim ring(0 To pairs - 1, 0 To 1)
                    For j = 0 To pairs - 1
                        ring(j, 0) = val(parts(1 + 2 * j))
                        ring(j, 1) = val(parts(2 + 2 * j))
                    Next j
                    v.dao.Add ring
                    v.NDao = v.dao.Count
                End If
        End Select
tt:
    Next i
    If Not v Is Nothing Then coll.Add v
    Set MoCSDL = coll
End Function


Private Function TenLevelActive() As String
    On Error Resume Next
    TenLevelActive = ActiveSettings.Level.Name
    On Error GoTo 0
End Function


'============================================================
' (1) TAO CSDL: ghep vung tu ranh -> luu file + ve tam
'============================================================
Public Sub DC_TaoCSDL()
    Dim lvRanh As String, snapStr As String, snap As Double, path As String
    lvRanh = InputBox("TEN level RANH (nhieu level cach nhau dau phay):", _
                      "Tao CSDL", TenLevelActive())
    snapStr = InputBox("Snap:", "Tao CSDL", "0.05")
    If snapStr = "" Then Exit Sub
    snap = val(snapStr): If snap <= 0 Then snap = 0.05
    path = InputBox("Duong dan file CSDL:", "Tao CSDL", "C:\DiaChinhVL\csdl_tobando.txt")
    If path = "" Then Exit Sub

    Dim minX As Double, minY As Double, maxX As Double, maxY As Double
    Dim segs As Collection
    Set segs = LayDoanNhieuLevel(lvRanh, snap, minX, minY, maxX, maxY)
    If segs.Count = 0 Then MsgBox "Khong doc duoc ranh.", vbExclamation: Exit Sub
    Dim tia As Long, vungs As Collection
    Set vungs = GhepVung(segs, snap, tia)
    If vungs.Count = 0 Then MsgBox "Khong ghep duoc vung.", vbExclamation: Exit Sub

    ' Ve tam de thay
    Dim size As Double
    size = ((maxX - minX) + (maxY - minY)) / 2# / 2000#
    If size <= 0 Then size = 0.3
    Dim i As Long, v As clsVung
    For i = 1 To vungs.Count
        Set v = vungs.Item(i)
        VeTamHong v.cx, v.cy, size, 5
    Next i

    Dim ok As Boolean
    ok = LuuCSDL(vungs, path)
    MsgBox "So thua tao: " & vungs.Count & vbCrLf & _
           IIf(ok, "Da luu CSDL: " & path, "KHONG luu duoc CSDL: " & path), _
           vbInformation, "Tao CSDL"
End Sub


'============================================================
' (2) XEM BANG DU LIEU: mo CSDL -> do ra Excel
'============================================================
Public Sub DC_XemBangDuLieu()
    Dim path As String
    path = InputBox("Duong dan file CSDL:", "Bang du lieu", "C:\DiaChinhVL\csdl_tobando.txt")
    If path = "" Then Exit Sub
    Dim vungs As Collection
    Set vungs = MoCSDL(path)
    If vungs.Count = 0 Then MsgBox "CSDL rong hoac khong doc duoc.", vbExclamation: Exit Sub

    Dim xl As Object, wb As Object, ws As Object
    On Error Resume Next
    Set xl = CreateObject("Excel.Application")
    On Error GoTo 0
    If xl Is Nothing Then MsgBox "Khong mo duoc Excel.", vbExclamation: Exit Sub
    xl.Visible = True
    Set wb = xl.Workbooks.Add
    Set ws = wb.Worksheets(1)
    ws.Cells(1, 1).Value = "STT"
    ws.Cells(1, 2).Value = "To ban do"
    ws.Cells(1, 3).Value = "So thua"
    ws.Cells(1, 4).Value = "Loai dat"
    ws.Cells(1, 5).Value = "Dien tich (m2)"
    ws.Cells(1, 6).Value = "Ten chu"
    ws.Cells(1, 7).Value = "Dia chi"
    ws.Range("A1:G1").Font.Bold = True

    Dim i As Long, v As clsVung, r As Long
    For i = 1 To vungs.Count
        Set v = vungs.Item(i)
        r = i + 1
        ws.Cells(r, 1).Value = i
        ws.Cells(r, 2).Value = v.SoTo
        ws.Cells(r, 3).Value = v.soThua
        ws.Cells(r, 4).Value = v.loaiDat
        ws.Cells(r, 5).Value = Round(v.dt, 1)
        ws.Cells(r, 6).Value = v.TenChu
        ws.Cells(r, 7).Value = v.DiaChi
    Next i
    ws.Cells(vungs.Count + 2, 4).Value = "Tong:"
    ws.Cells(vungs.Count + 2, 5).Formula = "=SUM(E2:E" & (vungs.Count + 1) & ")"
    ws.Columns("A:G").AutoFit

    MsgBox "Da mo bang du lieu: " & vungs.Count & " thua.", vbInformation, "Bang du lieu"
End Sub

Attribute VB_Name = "modCSDL2"
Option Explicit

'============================================================
' modCSDL2 - Buoc 3: Gan thong tin tu nhan vao CSDL + ve nhan
'   Mo CSDL -> gan cac truong tu level -> luu lai CSDL -> ve nhan.
'============================================================

Private Function DocMotText(ByVal el As Element, ByRef x As Double, _
                            ByRef y As Double, ByRef s As String) As Boolean
    DocMotText = False
    s = ""
    Dim o As Point3d
    If el.Type = msdElementTypeText Then
        Dim oT As TextElement
        Set oT = el
        o = oT.Origin: x = o.x: y = o.y
        s = Trim$(oT.Text)
        DocMotText = True
    ElseIf el.Type = msdElementTypeTextNode Then
        Dim oNode As TextNodeElement
        Set oNode = el
        o = oNode.Origin: x = o.x: y = o.y
        Dim subs As ElementEnumerator
        Set subs = oNode.GetSubElements
        Do While subs.MoveNext
            If subs.Current.Type = msdElementTypeText Then
                s = Trim$(subs.Current.AsTextElement.Text)
                If Len(s) > 0 Then Exit Do
            End If
        Loop
        DocMotText = True
    End If
End Function

Private Function LayTruong(ByVal v As clsVung, ByVal t As String) As String
    Select Case t
        Case "so_thua": LayTruong = v.soThua
        Case "so_to": LayTruong = v.SoTo
        Case "loai_dat": LayTruong = v.loaiDat
        Case "ten_chu": LayTruong = v.TenChu
        Case "dia_chi": LayTruong = v.DiaChi
    End Select
End Function

Private Sub DatTruong(ByVal v As clsVung, ByVal t As String, ByVal g As String)
    Select Case t
        Case "so_thua": v.soThua = g
        Case "so_to": v.SoTo = g
        Case "loai_dat": v.loaiDat = g
        Case "ten_chu": v.TenChu = g
        Case "dia_chi": v.DiaChi = g
    End Select
End Sub

Private Function GanTruongCSDL(ByVal vungs As Collection, ByVal levelName As String, _
                               ByVal truong As String) As Long
    If Len(Trim$(levelName)) = 0 Then Exit Function
    Dim esc As ElementScanCriteria
    Set esc = New ElementScanCriteria
    esc.ExcludeAllTypes
    esc.IncludeType msdElementTypeText
    esc.IncludeType msdElementTypeTextNode
    Dim lv As Level, lvSo As Long
    Set lv = DC_TimLevel(levelName)          ' go "13" = level so 13
    If lv Is Nothing Then Exit Function
    lvSo = lv.Number

    Dim ee As ElementEnumerator
    Set ee = ActiveModelReference.Scan(esc)
    Dim x As Double, y As Double, s As String, v As clsVung, dem As Long
    Do While ee.MoveNext
        If DC_LevelSo(ee.Current) = lvSo Then
        If DocMotText(ee.Current, x, y, s) Then
            If Len(s) > 0 Then
                Set v = TimThuaChua(vungs, x, y)
                If Not v Is Nothing Then
                    If Len(LayTruong(v, truong)) = 0 Then
                        DatTruong v, truong, s
                        dem = dem + 1
                    End If
                End If
            End If
        End If
        End If
    Loop
    GanTruongCSDL = dem
End Function


'============================================================
' (3) GAN THONG TIN TU NHAN VAO CSDL + VE NHAN
'============================================================
Public Sub DC_GanThongTinCSDL()
    Dim path As String
    path = InputBox("Duong dan file CSDL:", "Gan thong tin", "C:\DiaChinhVL\csdl_tobando.txt")
    If path = "" Then Exit Sub
    Dim vungs As Collection
    Set vungs = MoCSDL(path)
    If vungs.Count = 0 Then MsgBox "CSDL rong / khong doc duoc.", vbExclamation: Exit Sub

    Dim lvTo As String, lvSo As String, lvLoai As String, lvChu As String, lvDC As String
    lvSo = InputBox("Level SO HIEU THUA:", "Gan thong tin", "")
    lvTo = InputBox("Level TO BAN DO (de trong=bo qua):", "Gan thong tin", "")
    lvLoai = InputBox("Level LOAI DAT (de trong=bo qua):", "Gan thong tin", "")
    lvChu = InputBox("Level TEN CHU (de trong=bo qua):", "Gan thong tin", "")
    lvDC = InputBox("Level DIA CHI (de trong=bo qua):", "Gan thong tin", "")

    Dim nSo As Long, nTo As Long, nLoai As Long, nChu As Long, nDC As Long
    nSo = GanTruongCSDL(vungs, lvSo, "so_thua")
    nTo = GanTruongCSDL(vungs, lvTo, "so_to")
    nLoai = GanTruongCSDL(vungs, lvLoai, "loai_dat")
    nChu = GanTruongCSDL(vungs, lvChu, "ten_chu")
    nDC = GanTruongCSDL(vungs, lvDC, "dia_chi")

    ' Luu lai CSDL da co thuoc tinh
    Dim ok As Boolean
    ok = LuuCSDL(vungs, path)

    ' Ve nhan tu CSDL
    Dim lvNhan As String, caoStr As String, cao As Double
    lvNhan = InputBox("Lop nhan (ve nhan len level nay):", "Ve nhan", "6")
    caoStr = InputBox("Co chu nhan:", "Ve nhan", "1")
    cao = val(caoStr): If cao <= 0 Then cao = 1
    If Len(Trim$(lvNhan)) > 0 Then
        On Error Resume Next
        Set ActiveSettings.Level = DC_TimLevel(lvNhan)
        On Error GoTo 0
    End If
    Dim i As Long, v As clsVung
    For i = 1 To vungs.Count
        Set v = vungs.Item(i)
        VeNhanThuaDayDu v, cao, "mau"
    Next i

    MsgBox "So thua: " & vungs.Count & vbCrLf & _
           "Gan So thua: " & nSo & vbCrLf & _
           "Gan To ban do: " & nTo & vbCrLf & _
           "Gan Loai dat: " & nLoai & vbCrLf & _
           "Gan Ten chu: " & nChu & vbCrLf & _
           "Gan Dia chi: " & nDC & vbCrLf & _
           IIf(ok, "Da cap nhat CSDL.", "KHONG luu duoc CSDL!") & vbCrLf & _
           "Da ve nhan len " & lvNhan, _
           vbInformation, "Gan thong tin + ve nhan"
End Sub


'============================================================
' Ve lai nhan tu CSDL (khong gan lai)
'============================================================
Public Sub DC_VeNhanTuCSDL()
    Dim path As String
    path = InputBox("Duong dan file CSDL:", "Ve nhan tu CSDL", "C:\DiaChinhVL\csdl_tobando.txt")
    If path = "" Then Exit Sub
    Dim vungs As Collection
    Set vungs = MoCSDL(path)
    If vungs.Count = 0 Then MsgBox "CSDL rong.", vbExclamation: Exit Sub

    Dim lvNhan As String, caoStr As String, cao As Double
    lvNhan = InputBox("Lop nhan:", "Ve nhan", "6")
    caoStr = InputBox("Co chu:", "Ve nhan", "1")
    cao = val(caoStr): If cao <= 0 Then cao = 1
    If Len(Trim$(lvNhan)) > 0 Then
        On Error Resume Next
        Set ActiveSettings.Level = DC_TimLevel(lvNhan)
        On Error GoTo 0
    End If
    Dim i As Long, v As clsVung
    For i = 1 To vungs.Count
        Set v = vungs.Item(i)
        VeNhanThuaDayDu v, cao, "mau"
    Next i
    MsgBox "Da ve nhan " & vungs.Count & " thua tu CSDL.", vbInformation, "Ve nhan"
End Sub

Attribute VB_Name = "modCapNhat"
'============================================================
' modCapNhat - Tu dong nap code moi vao project DiaChinhVL
'   (khong can mo VBA IDE copy/dan bang tay nua)
'
' Cach dung: key-in
'   vba run [DiaChinhVL]modCapNhat.DC_CapNhatCode
'
' Lam gi:
'   - Doc moi file <TenModule>.txt trong D:\Claude\vba_v8\capnhat\
'   - Thay toan bo code cua module/class/form trung ten
'     (chua co module/class -> tu tao moi; form thi phai co san)
'   - Co DiaChinhVL.ico -> chep vao C:\DiaChinhVL\
'   - File da nap -> chuyen vao capnhat\_danap\ (lan sau khong nap lai)
'   - Luu project (vba save)
'============================================================
Option Explicit

Public Const DC_CAPNHAT As String = "D:\Claude\vba_v8\capnhat"
Private Const DC_DICH As String = "C:\DiaChinhVL"

Public Sub DC_CapNhatCode()
    Dim vbe As Object, prj As Object, p As Object, c As Object
    Dim dS As New Collection, f As Variant, ten As String, code As String
    Dim kq As String, i As Long, kieu As Long, nOK As Long

    '--- 1. Lay project DiaChinhVL qua VBE
    On Error Resume Next
    Set vbe = Application.vbe
    On Error GoTo 0
    If vbe Is Nothing Then
        MsgBox "Khong truy cap duoc VBE (Application.VBE)." & vbCrLf & _
               "Phai cap nhat bang tay (copy/dan).", vbCritical, "Cap nhat code"
        Exit Sub
    End If
    For Each p In vbe.VBProjects
        If StrComp(p.Name, "DiaChinhVL", vbTextCompare) = 0 Then Set prj = p: Exit For
    Next p
    If prj Is Nothing Then
        MsgBox "Khong thay project DiaChinhVL. Hay vba load truoc.", vbCritical, "Cap nhat code"
        Exit Sub
    End If

    '--- 2. Dong cac form dang mo (tranh sua code form dang chay)
    On Error Resume Next
    For i = UserForms.Count - 1 To 0 Step -1
        Unload UserForms(i)
    Next i
    On Error GoTo 0

    '--- 3. Chep logo
    If Len(Dir$(DC_CAPNHAT & "\DiaChinhVL.ico")) > 0 Then
        On Error Resume Next
        If Len(Dir$(DC_DICH, vbDirectory)) = 0 Then MkDir DC_DICH
        FileCopy DC_CAPNHAT & "\DiaChinhVL.ico", DC_DICH & "\DiaChinhVL.ico"
        If Err.Number = 0 Then kq = kq & "  [OK] logo -> " & DC_DICH & "\DiaChinhVL.ico" & vbCrLf _
                          Else kq = kq & "  [LOI] khong chep duoc logo: " & Err.Description & vbCrLf
        On Error GoTo 0
    End If

    '--- 4. Gom danh sach file .txt
    f = Dir$(DC_CAPNHAT & "\*.txt")
    Do While Len(f) > 0
        dS.Add CStr(f)
        f = Dir$()
    Loop

    '--- 5. Nap tung file
    For Each f In dS
        ten = Left$(f, Len(f) - 4)
        If StrComp(ten, "modCapNhat", vbTextCompare) = 0 Then
            kq = kq & "  [BO QUA] " & ten & " (khong tu thay chinh no)" & vbCrLf
            GoTo TiepTuc
        End If

        Set c = Nothing
        On Error Resume Next
        Set c = prj.VBComponents(ten)
        On Error GoTo 0

        If c Is Nothing Then
            Select Case LCase$(Left$(ten, 3))
            Case "frm"
                kq = kq & "  [LOI] " & ten & ": form chua co -> phai tao form trong IDE truoc" & vbCrLf
                GoTo TiepTuc
            Case "cls": kieu = 2      ' class module
            Case Else:  kieu = 1      ' standard module
            End Select
            Set c = prj.VBComponents.Add(kieu)
            c.Name = ten
            kq = kq & "  [MOI] " & ten & vbCrLf
        End If

        code = DocFile(DC_CAPNHAT & "\" & f)
        With c.CodeModule
            If .CountOfLines > 0 Then .DeleteLines 1, .CountOfLines
            .AddFromString code
        End With
        kq = kq & "  [OK] " & ten & vbCrLf
        nOK = nOK + 1
        DaNap CStr(f)
TiepTuc:
    Next f

    '--- 6. Luu project
    On Error Resume Next
    CadInputQueue.SendKeyin "vba save DiaChinhVL"
    On Error GoTo 0

    If Len(kq) = 0 Then kq = "  (khong co file nao trong " & DC_CAPNHAT & ")" & vbCrLf
    MsgBox "Ket qua cap nhat (" & nOK & " module):" & vbCrLf & vbCrLf & kq & vbCrLf & _
           "Mo lai menu: vba run [DiaChinhVL]modMoGiaoDien.DC_MoGiaoDien" & vbCrLf & _
           "(Neu sau do dong MicroStation ma hoi luu project -> chon Yes)", _
           vbInformation, "Cap nhat code"
End Sub

Private Function DocFile(ByVal path As String) As String
    Dim n As Integer, s As String
    n = FreeFile
    Open path For Binary Access Read As #n
    s = Space$(LOF(n))
    Get #n, , s
    Close #n
    DocFile = s
End Function

'--- chuyen file da nap vao _danap\ (ghi de neu trung ten)
Private Sub DaNap(ByVal f As String)
    On Error Resume Next
    Dim thu As String
    thu = DC_CAPNHAT & "\_danap"
    If Len(Dir$(thu, vbDirectory)) = 0 Then MkDir thu
    If Len(Dir$(thu & "\" & f)) > 0 Then Kill thu & "\" & f
    Name DC_CAPNHAT & "\" & f As thu & "\" & f
End Sub

Attribute VB_Name = "modCapNhatWeb"
'============================================================
' modCapNhatWeb - CAP NHAT TU XA qua GitHub (ban 2)
'   Kho: https://github.com/lehoangtuat/DiaChinhVL  (cong khai)
'   SUA 10/2026: KHONG con sua code trong MicroStation (cach cu bi treo
'   tren may loi VBA IDE). Gio chay C:\DiaChinhVL\CapNhat_DiaChinhVL.bat:
'   cho dong MicroStation roi THAY NGUYEN FILE DiaChinhVL.mvba.
'   Menu: Tro giup -> Kiem tra cap nhat
'============================================================
Option Explicit

Public Const DC_PHIENBAN_GOC As String = "1.0"
Public Const DC_URL_CAPNHAT As String = "https://raw.githubusercontent.com/lehoangtuat/DiaChinhVL/main/"

Public Function DC_PhienBan() As String
    DC_PhienBan = DC_DocCauHinh("PHIENBAN", DC_PHIENBAN_GOC)
End Function

Public Sub DC_KiemTraCapNhat()
    KiemTra True
End Sub

' Goi tu thong bao "co ban moi" khi mo menu (da hoi roi -> khong hoi lai)
Public Sub DC_CapNhatNgay()
    KiemTra False
End Sub

' Kiem tra nhanh khi mo menu (toi da 1 lan/ngay, mang cham thi bo qua).
' Tra ve so ban moi neu VUA phat hien, "" neu khong.
Public Function DC_BanMoiNhanh() As String
    Dim ngay As String, h As Object, v As String
    ngay = Format$(Date, "yyyymmdd")
    If DC_DocCauHinh("CN_NGAY", "") = ngay Then Exit Function
    DC_GhiCauHinh "CN_NGAY", ngay
    On Error Resume Next
    Set h = CreateObject("MSXML2.ServerXMLHTTP.6.0")
    If h Is Nothing Then Exit Function
    h.setTimeouts 2000, 3000, 3000, 4000
    h.Open "GET", DC_URL_CAPNHAT & "version.txt?t=" & Format$(Now, "yyyymmddhhnnss"), False
    h.setRequestHeader "Cache-Control", "no-cache"
    h.Send
    If Err.Number <> 0 Then Exit Function
    If h.Status <> 200 Then Exit Function
    v = Trim$(Split(Replace(h.responseText, vbCr, ""), vbLf)(0))
    If Len(v) = 0 Then Exit Function
    DC_GhiCauHinh "CN_MOI", v
    If SoSanhPB(v, DC_PhienBan()) > 0 Then DC_BanMoiNhanh = v
End Function

' Ban moi da biet tu lan kiem tra truoc (de hien nhan "Co ban moi")
Public Function DC_BanMoiDaBiet() As String
    Dim v As String
    v = DC_DocCauHinh("CN_MOI", "")
    If Len(v) > 0 Then
        If SoSanhPB(v, DC_PhienBan()) > 0 Then DC_BanMoiDaBiet = v
    End If
End Function

Private Sub KiemTra(ByVal Hoi As Boolean)
    Dim v As String, Dong() As String, moi As String, cu As String, ghiChu As String
    Dim i As Long, bat As String, pS As String, s As String

    ShowStatus "DiaChinhVL: dang kiem tra ban moi ..."
    v = TaiChuoi(DC_URL_CAPNHAT & "version.txt")
    ShowStatus ""
    If Len(Trim$(v)) = 0 Then
        DC_ThongBao "Kh" & ChrW(244) & "ng k" & ChrW(7871) & "t n" & ChrW(7889) & "i " & ChrW(273) & ChrW(432) & ChrW(7907) & "c m" & ChrW(225) & "y ch" & ChrW(7911) & " c" & ChrW(7853) & "p nh" & ChrW(7853) & "t (GitHub)." & vbCrLf & _
                    "Ki" & ChrW(7875) & "m tra m" & ChrW(7841) & "ng Internet r" & ChrW(7891) & "i th" & ChrW(7917) & " l" & ChrW(7841) & "i.", "C" & ChrW(7853) & "p nh" & ChrW(7853) & "t", vbExclamation
        Exit Sub
    End If
    Dong = Split(Replace(v, vbCr, ""), vbLf)
    moi = Trim$(Dong(0))
    For i = 1 To UBound(Dong)
        If Len(Trim$(Dong(i))) > 0 Then ghiChu = ghiChu & Dong(i) & vbCrLf
    Next i
    cu = DC_PhienBan()
    If SoSanhPB(moi, cu) <= 0 Then
        DC_ThongBao "B" & ChrW(7841) & "n " & ChrW(273) & "ang d" & ChrW(249) & "ng b" & ChrW(7843) & "n m" & ChrW(7899) & "i nh" & ChrW(7845) & "t (" & cu & ").", "C" & ChrW(7853) & "p nh" & ChrW(7853) & "t"
        Exit Sub
    End If
    If Hoi Then
    If DC_ThongBao("C" & ChrW(243) & " b" & ChrW(7843) & "n m" & ChrW(7899) & "i " & moi & " (" & ChrW(273) & "ang d" & ChrW(249) & "ng " & cu & ")." & vbCrLf & vbCrLf & _
                   ghiChu & vbCrLf & "C" & ChrW(7853) & "p nh" & ChrW(7853) & "t ngay?" & vbCrLf & _
                   "(MicroStation s" & ChrW(7869) & " t" & ChrW(7921) & " " & ChrW(273) & ChrW(243) & "ng, c" & ChrW(7853) & "p nh" & ChrW(7853) & "t xong t" & ChrW(7921) & " m" & ChrW(7903) & " l" & ChrW(7841) & "i b" & ChrW(7843) & "n v" & ChrW(7869) & " " & ChrW(273) & "ang l" & ChrW(224) & "m)", _
                   "C" & ChrW(7853) & "p nh" & ChrW(7853) & "t", vbYesNo Or vbQuestion) <> vbYes Then Exit Sub
    End If

    ' Lay ban moi nhat cua trinh cap nhat (.bat + .ps1) ve C:\DiaChinhVL
    bat = DC_THUMUC & "\CapNhat_DiaChinhVL.bat"
    pS = DC_THUMUC & "\CapNhat_DiaChinhVL.ps1"
    s = TaiChuoi(DC_URL_CAPNHAT & "CapNhat_DiaChinhVL.ps1")
    If Len(s) > 0 Then GhiAnsi pS, s
    s = TaiChuoi(DC_URL_CAPNHAT & "CapNhat_DiaChinhVL.bat")
    If Len(s) > 0 Then GhiAnsi bat, s
    If Len(Dir$(bat)) = 0 Or Len(Dir$(pS)) = 0 Then
        DC_ThongBao "Kh" & ChrW(244) & "ng t" & ChrW(7843) & "i " & ChrW(273) & ChrW(432) & ChrW(7907) & "c tr" & ChrW(236) & "nh c" & ChrW(7853) & "p nh" & ChrW(7853) & "t.", "C" & ChrW(7853) & "p nh" & ChrW(7853) & "t", vbExclamation
        Exit Sub
    End If

    ' Ghi ban ve dang mo de trinh cap nhat mo lai sau khi xong
    On Error Resume Next
    Dim nF As Integer
    nF = FreeFile
    Open DC_THUMUC & "\capnhat_molai.txt" For Output As #nF
    Print #nF, ActiveDesignFile.FullName
    Close #nF
    Err.Clear
    Shell "cmd /c """ & bat & """", vbNormalFocus
    If Err.Number <> 0 Then
        DC_ThongBao "Kh" & ChrW(244) & "ng ch" & ChrW(7841) & "y " & ChrW(273) & ChrW(432) & ChrW(7907) & "c: " & bat & vbCrLf & "H" & ChrW(227) & "y b" & ChrW(7845) & "m " & ChrW(273) & ChrW(250) & "p file " & ChrW(273) & ChrW(243) & " " & ChrW(273) & ChrW(7875) & " c" & ChrW(7853) & "p nh" & ChrW(7853) & "t.", "C" & ChrW(7853) & "p nh" & ChrW(7853) & "t", vbExclamation
        Exit Sub
    End If
    On Error GoTo 0
    ' Khong hien hop thoai nua: trinh cap nhat tu dong MicroStation, thay file, mo lai
    ShowStatus "DiaChinhVL: dang cap nhat len ban " & moi & " - MicroStation se tu dong va mo lai ..."
End Sub

Private Function TaiChuoi(ByVal url As String) As String
    Dim h As Object, lan As Long
    For lan = 1 To 3
        Set h = Nothing
        On Error Resume Next
        Set h = CreateObject("MSXML2.ServerXMLHTTP.6.0")
        If h Is Nothing Then Set h = CreateObject("WinHttp.WinHttpRequest.5.1")
        If h Is Nothing Then Exit Function
        Err.Clear
        h.setTimeouts 5000, 10000, 15000, 30000      ' khong treo may khi mang cham
        h.Open "GET", url & IIf(InStr(url, "?") > 0, "&", "?") & "t=" & Format$(Now, "yyyymmddhhnnss"), False
        h.setRequestHeader "Cache-Control", "no-cache"
        h.setRequestHeader "User-Agent", "DiaChinhVL"
        h.Send
        If Err.Number = 0 Then
            If h.Status = 200 Then TaiChuoi = h.responseText: Exit Function
        End If
        Err.Clear
        On Error GoTo 0
        DoEvents
    Next lan
End Function

Private Function GhiAnsi(ByVal path As String, ByVal s As String) As Boolean
    Dim n As Integer
    On Error GoTo Loi
    s = Replace(Replace(s, vbCrLf, vbLf), vbLf, vbCrLf)
    n = FreeFile
    Open path For Output As #n
    Print #n, s;
    Close #n
    GhiAnsi = True
    Exit Function
Loi:
    DC_ThongBao "Kh" & ChrW(244) & "ng ghi " & ChrW(273) & ChrW(432) & ChrW(7907) & "c file: " & path & vbCrLf & Err.Description, "C" & ChrW(7853) & "p nh" & ChrW(7853) & "t", vbExclamation
End Function

Private Function DocFile(ByVal path As String) As String
    Dim n As Integer, s As String
    n = FreeFile
    Open path For Binary Access Read As #n
    s = Space$(LOF(n))
    Get #n, , s
    Close #n
    DocFile = s
End Function

Private Function SoSanhPB(ByVal a As String, ByVal b As String) As Long
    Dim x() As String, y() As String, i As Long, va As Long, vb As Long, n As Long
    x = Split(a, "."): y = Split(b, ".")
    n = UBound(x): If UBound(y) > n Then n = UBound(y)
    For i = 0 To n
        va = 0: vb = 0
        If i <= UBound(x) Then va = val(x(i))
        If i <= UBound(y) Then vb = val(y(i))
        If va > vb Then SoSanhPB = 1: Exit Function
        If va < vb Then SoSanhPB = -1: Exit Function
    Next i
End Function

Attribute VB_Name = "modCauHinh"
'============================================================
' modCauHinh - Luu / doc thiet lap cua DiaChinhVL
'   File: C:\DiaChinhVL\DiaChinhVL.ini  (UTF-8, moi dong KHOA=gia tri)
'   Khoa dang dung: TINH, XA, HUYEN
'============================================================
Option Explicit

Public Const DC_CAUHINH As String = "C:\DiaChinhVL\DiaChinhVL.ini"

Public Function DC_DocCauHinh(ByVal khoa As String, Optional ByVal macDinh As String = "") As String
    Dim Dong() As String, i As Long, p As Long
    DC_DocCauHinh = macDinh
    Dong = Split(DocUtf8(DC_CAUHINH), vbLf)
    For i = LBound(Dong) To UBound(Dong)
        p = InStr(Dong(i), "=")
        If p > 1 Then
            If StrComp(Trim$(Left$(Dong(i), p - 1)), khoa, vbTextCompare) = 0 Then
                DC_DocCauHinh = Trim$(Replace(Mid$(Dong(i), p + 1), vbCr, ""))
                Exit Function
            End If
        End If
    Next i
End Function

Public Sub DC_GhiCauHinh(ByVal khoa As String, ByVal GiaTri As String)
    Dim Dong() As String, i As Long, p As Long, kq As String, daCo As Boolean
    Dim txt As String
    txt = DocUtf8(DC_CAUHINH)
    GiaTri = Replace(Replace(GiaTri, vbCr, " "), vbLf, " ")
    If Len(txt) > 0 Then
        Dong = Split(Replace(txt, vbCr, ""), vbLf)
        For i = LBound(Dong) To UBound(Dong)
            If Len(Trim$(Dong(i))) > 0 Then
                p = InStr(Dong(i), "=")
                If p > 1 Then
                    If StrComp(Trim$(Left$(Dong(i), p - 1)), khoa, vbTextCompare) = 0 Then
                        Dong(i) = khoa & "=" & GiaTri
                        daCo = True
                    End If
                End If
                kq = kq & Dong(i) & vbCrLf
            End If
        Next i
    End If
    If Not daCo Then kq = kq & khoa & "=" & GiaTri & vbCrLf
    GhiUtf8 DC_CAUHINH, kq
End Sub

Private Function DocUtf8(ByVal path As String) As String
    Dim st As Object
    If Len(Dir$(path)) = 0 Then Exit Function
    On Error Resume Next
    Set st = CreateObject("ADODB.Stream")
    st.Type = 2: st.Charset = "utf-8": st.Open
    st.LoadFromFile path
    If Err.Number = 0 Then DocUtf8 = st.ReadText(-1)
    st.Close
End Function

Private Sub GhiUtf8(ByVal path As String, ByVal txt As String)
    Dim st As Object, thu As String
    On Error Resume Next
    thu = Left$(path, InStrRev(path, "\") - 1)
    If Len(Dir$(thu, vbDirectory)) = 0 Then MkDir thu
    Set st = CreateObject("ADODB.Stream")
    st.Type = 2: st.Charset = "utf-8": st.Open
    st.WriteText txt
    st.SaveToFile path, 2          ' 2 = ghi de
    st.Close
    If Err.Number <> 0 Then
        MsgBox "Khong luu duoc thiet lap: " & path & vbCrLf & Err.Description, vbExclamation, "DiaChinhVL"
    End If
End Sub

Attribute VB_Name = "modChiaDoan"
'============================================================
' modChiaDoan - CHIA DOAN TAI GIAO DIEM (sua that tren ban ve)
'   Line / LineString tren cac level ranh: cho nao net khac cat ngang
'   hoac cham vao (dau mut nam giua net, net cat qua dinh) -> tach phan tu
'   thanh nhieu doan tai diem do (giu level, mau, net, do day).
'   Tuy chon: xoa doan DU ngan (ve lo qua giao diem, dau kia ho).
'   Truoc khi sua dat "mark" -> Undo duoc.
'============================================================
Option Explicit

' levelsCSV: "Level 10,Level 32" ; tol: snap ; duThua: xoa doan du < duThua (0 = khong)
' Tra ve so phan tu da chia.
Public Function DC_ChiaDoanGiao(ByVal levelsCSV As String, ByVal tol As Double, _
                                ByVal duThua As Double, Optional ByVal baoKetQua As Boolean = True) As Long
    Dim dS() As Long, c As Long, i As Long, lvOk As Object
    If tol <= 0 Then tol = 0.05
    Set lvOk = CreateObject("Scripting.Dictionary")
    c = DC_DsSoLevel(levelsCSV, dS)
    For i = 0 To c - 1
        lvOk(CStr(dS(i))) = True
    Next i
    If c = 0 Then Exit Function

    ' 1) Phan tu Line / LineString tren cac level
    Dim esc As New ElementScanCriteria, ee As ElementEnumerator, el As Element
    Dim els() As Element, nE As Long
    esc.ExcludeAllTypes
    esc.IncludeType msdElementTypeLine
    esc.IncludeType msdElementTypeLineString
    ReDim els(1 To 256)
    Set ee = ActiveModelReference.Scan(esc)
    ' SUA 08/11: bo qua net hong (toa do NaN) - truoc day gay loi 6 Overflow
    Dim ptsK() As Point3d, nHong As Long, viTriHong As String, q2 As Long
    Do While ee.MoveNext
        Set el = ee.Current
        If lvOk.Exists(CStr(DC_LevelSo(el))) Then
            ptsK = el.AsVertexList.GetVertices
            If DC_DinhHopLe(ptsK) Then
                nE = nE + 1
                If nE > UBound(els) Then ReDim Preserve els(1 To nE * 2)
                Set els(nE) = el
            Else
                nHong = nHong + 1
                If nHong <= 5 Then
                    For q2 = LBound(ptsK) To UBound(ptsK)
                        If DC_SoHopLe(ptsK(q2).x) And DC_SoHopLe(ptsK(q2).y) Then
                            viTriHong = viTriHong & vbCrLf & "  - l" & ChrW(7899) & "p " & DC_LevelSo(el) & ", " & ChrW(273) & ChrW(7847) & "u c" & ChrW(242) & "n l" & ChrW(7841) & "i: X=" & Format$(ptsK(q2).x, "0.000") & "  Y=" & Format$(ptsK(q2).y, "0.000")
                            Exit For
                        End If
                    Next q2
                End If
            End If
        End If
    Loop
    If nHong > 0 Then
        DC_ThongBao "C" & ChrW(243) & " " & nHong & " n" & ChrW(233) & "t ranh b" & ChrW(7883) & " H" & ChrW(7886) & "NG t" & ChrW(7885) & "a " & ChrW(273) & ChrW(7897) & " (NaN) - " & ChrW(273) & ChrW(227) & " b" & ChrW(7887) & " qua, n" & ChrW(234) & "n x" & ChrW(243) & "a:" & viTriHong & vbCrLf & vbCrLf & _
                    "C" & ChrW(225) & "ch x" & ChrW(243) & "a: ph" & ChrW(243) & "ng t" & ChrW(7899) & "i t" & ChrW(7885) & "a " & ChrW(273) & ChrW(7897) & " tr" & ChrW(234) & "n, ch" & ChrW(7885) & "n n" & ChrW(233) & "t " & ChrW(273) & "i ra t" & ChrW(7915) & " " & ChrW(273) & "i" & ChrW(7875) & "m " & ChrW(273) & ChrW(243) & " (Element Selection) r" & ChrW(7891) & "i Delete.", "Chia " & ChrW(273) & "o" & ChrW(7841) & "n", vbExclamation
    End If
    If nE = 0 Then Exit Function

    ' 2) Doan thang + chu so phan tu / so dinh
    Dim pts() As Point3d, nS As Long, k As Long, e As Long
    Dim ax() As Double, ay() As Double, bx() As Double, by() As Double, dl() As Double
    Dim sE() As Long, sv() As Long, nV() As Long
    ReDim nV(1 To nE)
    For e = 1 To nE
        pts = els(e).AsVertexList.GetVertices
        nV(e) = UBound(pts) - LBound(pts) + 1
        nS = nS + nV(e) - 1
    Next e
    ReDim ax(1 To nS): ReDim ay(1 To nS): ReDim bx(1 To nS): ReDim by(1 To nS): ReDim dl(1 To nS)
    ReDim sE(1 To nS): ReDim sv(1 To nS)
    nS = 0
    For e = 1 To nE
        pts = els(e).AsVertexList.GetVertices
        For k = LBound(pts) To UBound(pts) - 1
            nS = nS + 1
            ax(nS) = pts(k).x: ay(nS) = pts(k).y: bx(nS) = pts(k + 1).x: by(nS) = pts(k + 1).y
            dl(nS) = Sqr((bx(nS) - ax(nS)) ^ 2 + (by(nS) - ay(nS)) ^ 2)
            sE(nS) = e: sv(nS) = k - LBound(pts)
        Next k
    Next e

    ' 3) Diem cat (luoi o vuong, modHinhHoc)
    Dim tL() As Collection
    ReDim tL(1 To nS)
    For i = 1 To nS
        Set tL(i) = New Collection
        tL(i).Add Array(0#, ax(i), ay(i))
        tL(i).Add Array(1#, bx(i), by(i))
    Next i
    LuoiGiaoCat nS, ax, ay, bx, by, dl, tol, tL

    ' 3b) Dinh giua cua LineString trung voi dau mut / dinh cua phan tu KHAC
    Dim dinh As Object, key As String
    Set dinh = CreateObject("Scripting.Dictionary")        ' o tol -> Collection Array(x, y, e)
    For e = 1 To nE
        pts = els(e).AsVertexList.GetVertices
        For k = LBound(pts) To UBound(pts)
            ThemDinh dinh, pts(k).x, pts(k).y, e, tol
        Next k
    Next e

    ' 4) Cat tung phan tu
    Dim cat() As Boolean, them() As Collection, j As Long, q As Long, a As Variant
    Dim nChia As Long, nDu As Long, moi As Collection, m As Long
    Dim dsMoi As New Collection, dsGoc As New Collection, laDu As New Collection
    For e = 1 To nE
        pts = els(e).AsVertexList.GetVertices
        m = nV(e)
        ReDim cat(0 To m - 1)
        ReDim them(0 To m - 1)
        For k = 0 To m - 1
            Set them(k) = New Collection
        Next k
        ' dinh giua trung voi phan tu khac
        For k = 1 To m - 2
            If CoPhanTuKhac(dinh, pts(LBound(pts) + k).x, pts(LBound(pts) + k).y, e, tol) Then cat(k) = True
        Next k
        ' dau mut cua phan tu co noi vao net khac khong (de nhan biet doan du)
        Dim noiDau As Boolean, noiCuoi As Boolean
        noiDau = CoPhanTuKhac(dinh, pts(LBound(pts)).x, pts(LBound(pts)).y, e, tol)
        noiCuoi = CoPhanTuKhac(dinh, pts(UBound(pts)).x, pts(UBound(pts)).y, e, tol)
        ' diem cat tren tung doan
        For i = 1 To nS
            If sE(i) = e Then
                k = sv(i)
                For q = 3 To tL(i).Count
                    a = tL(i).Item(q)
                    If a(0) <= tol / IIf(dl(i) > 0, dl(i), 1) Then
                        If k > 0 Then cat(k) = True Else noiDau = True
                    ElseIf a(0) >= 1# - tol / IIf(dl(i) > 0, dl(i), 1) Then
                        If k + 1 < m - 1 Then cat(k + 1) = True Else noiCuoi = True
                    Else
                        ThemTheoT them(k), a
                    End If
                Next q
            End If
        Next i
        ' co cat khong?
        Dim coCat As Boolean
        coCat = False
        For k = 0 To m - 1
            If cat(k) Or them(k).Count > 0 Then coCat = True: Exit For
        Next k
        If coCat Then
            ' day diem moi: dinh goc + diem chen ; danh dau diem cat
            Dim px As New Collection, py As New Collection, pC As New Collection
            Set px = New Collection: Set py = New Collection: Set pC = New Collection
            For k = 0 To m - 1
                px.Add pts(LBound(pts) + k).x: py.Add pts(LBound(pts) + k).y: pC.Add cat(k)
                If k < m - 1 Then
                    For q = 1 To them(k).Count
                        a = them(k).Item(q)
                        px.Add a(1): py.Add a(2): pC.Add True
                    Next q
                End If
            Next k
            ' cac doan con
            Dim batDau As Long, idx As Long
            batDau = 1
            For idx = 2 To px.Count
                If pC.Item(idx) Or idx = px.Count Then
                    If idx > batDau Then
                        dsMoi.Add DoanCon(px, py, batDau, idx)
                        dsGoc.Add e
                        ' doan du: dau ngoai la dau mut TU DO cua phan tu, dau trong la diem cat
                        laDu.Add (DoDai(px, py, batDau, idx) < duThua And _
                                  ((batDau = 1 And Not noiDau And idx < px.Count) Or _
                                   (idx = px.Count And Not noiCuoi And batDau > 1)))
                    End If
                    batDau = idx
                End If
            Next idx
            nChia = nChia + 1
        End If
    Next e
    If nChia = 0 Then
        If baoKetQua Then MsgBox "Khong co cho nao can chia doan.", vbInformation, "Chia doan"
        Exit Function
    End If

    ' 5) Doan du: chi xoa khi dau tu do khong cham phan tu nao khac
    Dim xoa() As Boolean, d As Variant
    ReDim xoa(1 To dsMoi.Count)
    For i = 1 To dsMoi.Count
        If duThua > 0 And laDu.Item(i) Then
            xoa(i) = True: nDu = nDu + 1
        End If
    Next i

    ' 6) Ghi ban ve: mark (undo), xoa phan tu goc, them doan moi
    On Error Resume Next
    CadInputQueue.SendKeyin "mark"
    Dim thay As Object
    Set thay = CreateObject("Scripting.Dictionary")
    For i = 1 To dsMoi.Count
        thay(CStr(dsGoc.Item(i))) = True
    Next i
    Dim e2 As Element, p2() As Point3d, nP As Long
    For i = 1 To dsMoi.Count
        If Not xoa(i) Then
            d = dsMoi.Item(i)
            nP = (UBound(d) + 1) \ 2
            ReDim p2(0 To nP - 1)
            For q = 0 To nP - 1
                p2(q).x = d(2 * q): p2(q).y = d(2 * q + 1): p2(q).Z = 0#
            Next q
            Set e2 = Nothing
            If nP = 2 Then
                Set e2 = CreateLineElement2(els(dsGoc.Item(i)), p2(0), p2(1))
            Else
                Set e2 = CreateLineElement1(els(dsGoc.Item(i)), p2)
            End If
            If Not e2 Is Nothing Then ActiveModelReference.AddElement e2
        End If
    Next i
    Dim kk As Variant
    For Each kk In thay.Keys
        ActiveModelReference.RemoveElement els(CLng(kk))
    Next kk
    On Error GoTo 0
    RedrawAllViews

    DC_ChiaDoanGiao = nChia
    If baoKetQua Then
        MsgBox "Da chia " & nChia & " net tai giao diem." & _
               IIf(nDu > 0, vbCrLf & "Da xoa " & nDu & " doan du (< " & duThua & " m).", "") & vbCrLf & _
               "(Sai: bam Undo hoac key-in: undo mark)", vbInformation, "Chia doan"
    End If
End Function

' Menu Bien tap -> Chia doan tai giao diem
Public Sub DC_MoChiaDoan()
    Dim lv As String, du As String
    lv = InputBox("Level ranh can chia doan (vd 10,32):", "Chia doan tai giao diem", DC_DocCauHinh("CHIA_LV", "10"))
    If Len(Trim$(lv)) = 0 Then Exit Sub
    du = InputBox("Xoa doan DU (ve lo qua giao diem) ngan hon (m), 0 = khong xoa:", "Chia doan tai giao diem", DC_DocCauHinh("CHIA_DU", "0.5"))
    DC_GhiCauHinh "CHIA_LV", lv
    DC_GhiCauHinh "CHIA_DU", du
    DC_ChiaDoanGiao lv, 0.05, val(du), True
End Sub

'------------------------------------------------------------
Private Sub ThemDinh(ByVal dinh As Object, ByVal x As Double, ByVal y As Double, ByVal e As Long, ByVal tol As Double)
    Dim key As String
    key = Int(x / tol) & "|" & Int(y / tol)
    If Not dinh.Exists(key) Then dinh.Add key, New Collection
    dinh(key).Add Array(x, y, e)
End Sub

' Co dinh cua phan tu khac (khac e) trong pham vi tol quanh (x, y)
Private Function CoPhanTuKhac(ByVal dinh As Object, ByVal x As Double, ByVal y As Double, _
                              ByVal e As Long, ByVal tol As Double) As Boolean
    Dim gx As Long, gy As Long, dx As Long, dy As Long, key As String, c As Collection, i As Long, a As Variant
    gx = Int(x / tol): gy = Int(y / tol)
    For dx = -1 To 1
        For dy = -1 To 1
            key = (gx + dx) & "|" & (gy + dy)
            If dinh.Exists(key) Then
                Set c = dinh(key)
                For i = 1 To c.Count
                    a = c.Item(i)
                    If a(2) <> e And Abs(a(0) - x) <= tol And Abs(a(1) - y) <= tol Then CoPhanTuKhac = True: Exit Function
                Next i
            End If
        Next dy
    Next dx
End Function

' Chen diem (t, x, y) vao danh sach theo t tang dan, bo trung
Private Sub ThemTheoT(ByVal c As Collection, ByVal a As Variant)
    Dim i As Long, b As Variant
    For i = 1 To c.Count
        b = c.Item(i)
        If Abs(b(0) - a(0)) < 0.0000001 Then Exit Sub
        If b(0) > a(0) Then c.Add a, Before:=i: Exit Sub
    Next i
    c.Add a
End Sub

Private Function DoanCon(ByVal px As Collection, ByVal py As Collection, ByVal i1 As Long, ByVal i2 As Long) As Variant
    Dim r() As Double, i As Long, n As Long
    ReDim r(0 To 2 * (i2 - i1 + 1) - 1)
    For i = i1 To i2
        r(n) = px.Item(i): r(n + 1) = py.Item(i): n = n + 2
    Next i
    DoanCon = r
End Function

Private Function DoDai(ByVal px As Collection, ByVal py As Collection, ByVal i1 As Long, ByVal i2 As Long) As Double
    Dim i As Long
    For i = i1 To i2 - 1
        DoDai = DoDai + Sqr((px.Item(i + 1) - px.Item(i)) ^ 2 + (py.Item(i + 1) - py.Item(i)) ^ 2)
    Next i
End Function

Attribute VB_Name = "modChieuDai"
'============================================================
' modChieuDai - "Chieu dai canh" (kieu "Ban do canh" LandMap)
'   Ghi chieu dai canh thua: nguon = doi tuong dang chon, hoac Fence,
'   hoac tat ca line/linestring/shape tren "Lop can hien". Canh chung
'   2 thua chi ghi 1 lan. Chu dat song song canh, ra phia ngoai thua.
'   Form: frmChieuDaiCanh (tao dong). Thong so luu ini (CDC_*).
'============================================================
Option Explicit

Private mDa As Object          ' khoa canh / dinh da ghi
Private mH As Double, mKc As Double, mSoLe As Long, mPhay As Boolean
Private mMau As Long, mMin As Double, mMoc As Boolean
Private mLvOut As Level, mFont As Object, mNChu As Long, mNMoc As Long

Public Sub DC_MoChieuDaiCanh()
    DC_MoFormTuTao "frmChieuDaiCanh"
End Sub

' Tra ve so canh da ghi (nMoc = so moc dinh)
Public Function CDC_ThucHien(ByVal tenFont As String, ByVal h As Double, ByVal mau As Long, _
                             ByVal kc As Double, ByVal SoLe As Long, ByVal lvVao As String, _
                             ByVal lvRa As String, ByVal minDai As Double, ByVal dungFence As Boolean, _
                             ByVal dauPhay As Boolean, ByVal taoMoc As Boolean, ByRef nMoc As Long, _
                             ByRef Loi As String) As Long
    Dim dS As New Collection, ee As ElementEnumerator, lvV As Level, esc As ElementScanCriteria
    mH = h: mKc = kc: mSoLe = SoLe: mPhay = dauPhay: mMau = mau: mMin = minDai: mMoc = taoMoc
    mNChu = 0: mNMoc = 0
    Set mDa = CreateObject("Scripting.Dictionary")
    If h <= 0 Then Loi = "K" & ChrW(237) & "ch th" & ChrW(432) & ChrW(7899) & "c ch" & ChrW(7919) & " ph" & ChrW(7843) & "i > 0.": Exit Function

    Set mLvOut = Nothing
    If Len(Trim$(lvRa)) > 0 Then
        If IsNumeric(Trim$(lvRa)) Then Set mLvOut = DC_LevelTheoSo(CLng(val(lvRa))) Else Set mLvOut = DC_TimLevel(lvRa)
        If mLvOut Is Nothing Then
            On Error Resume Next
            Set mLvOut = ActiveDesignFile.AddNewLevel(Trim$(lvRa))
            ActiveDesignFile.Levels.Rewrite
            On Error GoTo 0
        End If
    End If
    Set mFont = TimFontCD(tenFont)

    ' 1) Doi tuong dang chon
    On Error Resume Next
    Set ee = ActiveModelReference.GetSelectedElements
    On Error GoTo 0
    If Not ee Is Nothing Then
        Do While ee.MoveNext
            dS.Add ee.Current
        Loop
    End If
    ' 2) Fence / 3) ca level
    If dS.Count = 0 Then
        If Len(Trim$(lvVao)) > 0 Then Set lvV = DC_TimLevel(lvVao)
        If dungFence Then
            Dim oF As Object
            Set ee = Nothing
            On Error Resume Next
            Set oF = ActiveDesignFile
            If oF.Fence.IsDefined Then Set ee = oF.Fence.GetContents
            On Error GoTo 0
            If ee Is Nothing Then Loi = "Ch" & ChrW(432) & "a " & ChrW(273) & ChrW(7863) & "t Fence.": Exit Function
            Do While ee.MoveNext
                If lvV Is Nothing Then
                    dS.Add ee.Current
                ElseIf DC_LevelSo(ee.Current) = lvV.Number Then
                    dS.Add ee.Current
                End If
            Loop
        Else
            If lvV Is Nothing Then Loi = "Kh" & ChrW(244) & "ng t" & ChrW(236) & "m th" & ChrW(7845) & "y l" & ChrW(7899) & "p c" & ChrW(7847) & "n hi" & ChrW(7879) & "n: " & lvVao: Exit Function
            Set esc = New ElementScanCriteria
            esc.ExcludeAllTypes
            esc.IncludeType msdElementTypeLine
            esc.IncludeType msdElementTypeLineString
            esc.IncludeType msdElementTypeShape
            esc.IncludeType msdElementTypeComplexString
            esc.IncludeType msdElementTypeComplexShape
            esc.ExcludeAllLevels
            esc.IncludeLevel lvV
            Set ee = ActiveModelReference.Scan(esc)
            Do While ee.MoveNext
                dS.Add ee.Current
            Loop
        End If
    End If
    If dS.Count = 0 Then Loi = "Kh" & ChrW(244) & "ng c" & ChrW(243) & " c" & ChrW(7841) & "nh n" & ChrW(224) & "o (ch" & ChrW(7885) & "n " & ChrW(273) & ChrW(7889) & "i t" & ChrW(432) & ChrW(7907) & "ng, d" & ChrW(249) & "ng Fence, ho" & ChrW(7863) & "c ki" & ChrW(7875) & "m tra L" & ChrW(7899) & "p c" & ChrW(7847) & "n hi" & ChrW(7879) & "n).": Exit Function

    On Error Resume Next
    CadInputQueue.SendKeyin "mark"
    On Error GoTo 0
    Dim i As Long
    For i = 1 To dS.Count
        MotPhanTu dS.Item(i)
    Next i
    RedrawAllViews
    nMoc = mNMoc
    CDC_ThucHien = mNChu
End Function

Private Sub MotPhanTu(ByVal el As Element)
    Dim subs As ElementEnumerator, pts() As Point3d, i As Long, a As Double, chieu As Double
    On Error Resume Next
    If el.IsComplexElement And Not el.IsVertexList Then
        Set subs = el.AsComplexElement.GetSubElements
        Do While subs.MoveNext
            MotPhanTu subs.Current
        Loop
        Exit Sub
    End If
    If Not el.IsVertexList Then Exit Sub
    Err.Clear
    pts = el.AsVertexList.GetVertices
    If Err.Number <> 0 Then Exit Sub
    For i = LBound(pts) To UBound(pts) - 1
        a = a + pts(i).x * pts(i + 1).y - pts(i + 1).x * pts(i).y
    Next i
    If a >= 0 Then chieu = 1# Else chieu = -1#
    For i = LBound(pts) To UBound(pts) - 1
        GhiCanhCD pts(i).x, pts(i).y, pts(i + 1).x, pts(i + 1).y, chieu
    Next i
    If mMoc Then
        For i = LBound(pts) To UBound(pts)
            VeMoc pts(i).x, pts(i).y
        Next i
    End If
End Sub

Private Function khoa(ByVal x As Double, ByVal y As Double) As String
    khoa = Format$(Round(x, 3), "0.000") & "|" & Format$(Round(y, 3), "0.000")
End Function

Private Sub GhiCanhCD(ByVal ax As Double, ByVal ay As Double, ByVal bx As Double, ByVal by As Double, ByVal chieu As Double)
    Dim dx As Double, dy As Double, L As Double, ang As Double, mx As Double, my As Double
    Dim f As String, s As String, k1 As String, k2 As String, d As Double
    dx = bx - ax: dy = by - ay
    L = Sqr(dx * dx + dy * dy)
    If L <= 0.0001 Then Exit Sub
    If L <= mMin Then Exit Sub
    k1 = khoa(ax, ay): k2 = khoa(bx, by)
    If k1 > k2 Then s = k2 & "#" & k1 Else s = k1 & "#" & k2
    If mDa.Exists("C" & s) Then Exit Sub
    mDa("C" & s) = True
    ang = Atan2(dy, dx)
    If ang > 1.5708 Then ang = ang - 3.14159265358979
    If ang <= -1.5708 Then ang = ang + 3.14159265358979
    d = mKc + mH * 0.5                         ' tam chu cach canh
    mx = (ax + bx) / 2# + dy / L * d * chieu
    my = (ay + by) / 2# - dx / L * d * chieu
    If mSoLe <= 0 Then f = "0" Else f = "0." & String$(mSoLe, "0")
    s = Format$(L, f)
    If mPhay Then s = Replace(s, ".", ",") Else s = Replace(s, ",", ".")
    Dim oT As TextElement, ts As TextStyle
    On Error Resume Next
    Set oT = CreateTextElement1(Nothing, s, Point3dFromXYZ(mx, my, 0#), Matrix3dFromAxisAndRotationAngle(2, ang))
    If oT Is Nothing Then Exit Sub
    Set ts = oT.TextStyle
    ts.Height = mH: ts.Width = mH * 0.774
    ts.Justification = msdTextJustificationCenterCenter
    If Not mFont Is Nothing Then Set ts.Font = mFont
    Set oT.TextStyle = ts
    oT.color = mMau
    oT.LineWeight = 0
    If Not mLvOut Is Nothing Then Set oT.Level = mLvOut
    ActiveModelReference.AddElement oT
    mNChu = mNChu + 1
End Sub

Private Sub VeMoc(ByVal x As Double, ByVal y As Double)
    Dim k As String, e As Element, r As Double
    k = "M" & khoa(x, y)
    If mDa.Exists(k) Then Exit Sub
    mDa(k) = True
    r = mH * 0.15
    On Error Resume Next
    Set e = CreateEllipseElement2(Nothing, Point3dFromXYZ(x, y, 0#), r, r, Matrix3dIdentity)
    If e Is Nothing Then Exit Sub
    e.color = mMau
    e.LineWeight = 0
    If Not mLvOut Is Nothing Then Set e.Level = mLvOut
    ActiveModelReference.AddElement e
    mNMoc = mNMoc + 1
End Sub

Private Function TimFontCD(ByVal ten As String) As Object
    Dim f As Object
    On Error Resume Next
    If Len(Trim$(ten)) = 0 Then ten = DC_FONT_VIET
    For Each f In ActiveDesignFile.Fonts
        If StrComp(f.Name, Trim$(ten), vbTextCompare) = 0 Then Set TimFontCD = f: Exit Function
    Next f
End Function

' Danh sach ten font / ten level cho combo
Public Function CDC_DsFont() As Collection
    Dim c As New Collection, f As Object, d As Object
    Set d = CreateObject("Scripting.Dictionary"): d.CompareMode = 1
    On Error Resume Next
    For Each f In ActiveDesignFile.Fonts
        If Not d.Exists(f.Name) Then d(f.Name) = True: c.Add f.Name
    Next f
    Set CDC_DsFont = c
End Function

Public Function CDC_DsLevel() As Collection
    Dim c As New Collection, lv As Level
    On Error Resume Next
    For Each lv In ActiveDesignFile.Levels
        c.Add lv.Name
    Next lv
    Set CDC_DsLevel = c
End Function

Attribute VB_Name = "modChonThuaTL"
'============================================================
' modChonThuaTL - khoi dong che do "Chon thua tren ban do" de trich luc.
'   Giu tham chieu cong cu o bien module de no song suot lenh.
'============================================================
Option Explicit

Public gToolTL As clsChonThuaTL

Public Sub DC_ChonThuaTrichLuc(ByVal csdl As String, ByVal mau As String, ByVal kieu As String, _
        ByVal toBanDo As String, ByVal xa As String, ByVal huyen As String, ByVal tinh As String, _
        ByVal lvXuat As String, ByVal cao As Double, ByVal cheDoMau As Boolean, ByVal tyLe As Double, _
        Optional ByVal cheDo As Long = 0, Optional ByVal ini As String = "", Optional ByVal lvCat As String = "")

    Dim vungs As Collection
    Set vungs = MoCSDL(csdl)
    If vungs.Count = 0 Then
        DC_ThongBao "CSDL r" & ChrW(7895) & "ng / kh" & ChrW(244) & "ng " & ChrW(273) & ChrW(7885) & "c " & ChrW(273) & ChrW(432) & ChrW(7907) & "c:" & vbCrLf & csdl & vbCrLf & _
                    "H" & ChrW(227) & "y ch" & ChrW(7841) & "y T" & ChrW(7841) & "o Topology/CSDL cho t" & ChrW(7901) & " b" & ChrW(7843) & "n " & ChrW(273) & ChrW(7891) & " n" & ChrW(224) & "y tr" & ChrW(432) & ChrW(7899) & "c.", "Tr" & ChrW(237) & "ch l" & ChrW(7909) & "c", vbExclamation
        frmTrichLuc.Show vbModeless
        Exit Sub
    End If

    Set gToolTL = New clsChonThuaTL
    With gToolTL
        Set .vungs = vungs
        .csdl = csdl: .mau = mau: .kieu = kieu: .toBanDo = toBanDo
        .xa = xa: .huyen = huyen: .tinh = tinh: .lvXuat = lvXuat
        .cao = cao: .cheDoMau = cheDoMau: .tyLe = tyLe
        .cheDo = cheDo: .ini = ini: .lvCat = lvCat
    End With
    CommandState.StartPrimitive gToolTL
End Sub

Attribute VB_Name = "modConvertFont"
'============================================================
' modConvertFont - Convert font hang loat nhieu file DGN
'   Form: frmConvertFont (tao dong). Menu Tien ich -> "CFONT".
'   Kieu 0: TCVN3 (.VnTime/.VnTimeH...) -> Unicode (Times New Roman)
'   Kieu 1: Unicode -> TCVN3 (.VnTime ; chu hoa co dau -> .VnTimeH)
'   Loc theo Level.Number (-1 = tat ca lop).
'   File khac file hien tai: OpenDesignFileForProgram -> sua -> Save -> Close.
'============================================================
Option Explicit

Private Type CF_OFN
    lStructSize As Long
    hwndOwner As Long
    hInstance As Long
    lpstrFilter As Long
    lpstrCustomFilter As Long
    nMaxCustFilter As Long
    nFilterIndex As Long
    lpstrFile As Long
    nMaxFile As Long
    lpstrFileTitle As Long
    nMaxFileTitle As Long
    lpstrInitialDir As Long
    lpstrTitle As Long
    flags As Long
    nFileOffset As Integer
    nFileExtension As Integer
    lpstrDefExt As Long
    lCustData As Long
    lpfnHook As Long
    lpTemplateName As Long
End Type

Private Declare Function CF_GetOpenFileNameW Lib "comdlg32.dll" Alias "GetOpenFileNameW" (pOpenfilename As CF_OFN) As Long
Private Declare Function CF_GetActiveWindow Lib "user32" Alias "GetActiveWindow" () As Long

Private Const TCVN_MAP As String = "A10102,A200C2,A300CA,A400D4,A501A0,A601AF,A70110,A80103,A900E2,AA00EA,AB00F4,AC01A1,AD01B0,AE0111,B500E0,B61EA3,B700E3,B800E1,B91EA1,BB1EB1,BC1EB3,BD1EB5,BE1EAF,C61EB7,C71EA7,C81EA9,C91EAB,CA1EA5,CB1EAD,CC00E8,CE1EBB,CF1EBD,D000E9,D11EB9,D21EC1,D31EC3,D41EC5,D51EBF,D61EC7,D700EC,D81EC9,DC0129,DD00ED,DE1ECB,DF00F2,E11ECF,E200F5,E300F3,E41ECD,E51ED3,E61ED5,E71ED7,E81ED1,E91ED9,EA1EDD,EB1EDF,EC1EE1,ED1EDB,EE1EE3,EF00F9,F11EE7,F20169,F300FA,F41EE5,F51EEB,F61EED,F71EEF,F81EE9,F91EF1,FA1EF3,FB1EF7,FC1EF9,FD00FD,FE1EF5"

Private mRev As Object          ' Unicode -> byte TCVN3
Private mFwd As Object          ' byte TCVN3 -> Unicode
Private mByte As Object         ' ky tu ma 1252/1258 (>255) -> byte goc
Private Const BYTE_MAP As String = "0102C3,0103E3,0110D0,0111F0,01528C,01539C,01608A,01619A,01789F,017D8E,017E9E,019283,01A0D5,01A1F5,01AFDD,01B0FD,02C688,02DC98,0300CC,0301EC,0303DE,0309D2,0323F2,201396,201497,201891,201992,201A82,201C93,201D94,201E84,202086,202187,202295,202685,203089,20398B,203A9B,20ABFE,20AC80,212299"
Public CF_FileMoi As String     ' file V8 moi tao khi file goc la V7 ("" neu khong)
Private Const FONT_TCVN As String = ".VnTime"
Private Const FONT_TCVN_H As String = ".VnTimeH"

Public Function CF_TieuDe() As String
    CF_TieuDe = "DiaChinhVL"
End Function

'============================================================
' MO FORM (menu). Form chua co -> tu tao tu capnhat\<tenForm>.txt
'   Dung chung: DC_MoFormTuTao "frmConvertFont" / "frmTachLop" ...
'============================================================
Public Sub DC_MoConvertFont()
    DC_MoFormTuTao "frmConvertFont"
End Sub

Public Sub DC_MoFormTuTao(ByVal tenForm As String)
    Dim f As Object, msg As String
    On Error Resume Next
    Set f = VBA.UserForms.Add(tenForm)
    If f Is Nothing Then
        msg = Err.Description
        Err.Clear
        On Error GoTo 0
        If CoForm(tenForm) Then
            DC_ThongBao "L" & ChrW(7895) & "i m" & ChrW(7903) & " form " & tenForm & ": " & msg, CF_TieuDe, vbExclamation
        Else
            TaoForm tenForm
        End If
        Exit Sub
    End If
    On Error GoTo 0
    f.Show vbModeless
End Sub

Private Function CoForm(ByVal tenForm As String) As Boolean
    Dim p As Object, c As Object
    On Error Resume Next
    For Each p In Application.vbe.VBProjects
        If StrComp(p.Name, "DiaChinhVL", vbTextCompare) = 0 Then
            Set c = p.VBComponents(tenForm)
            CoForm = Not (c Is Nothing)
            Exit Function
        End If
    Next p
End Function

Private Sub TaoForm(ByVal tenForm As String)
    Dim prj As Object, p As Object, c As Object, src As String, code As String
    On Error Resume Next
    For Each p In Application.vbe.VBProjects
        If StrComp(p.Name, "DiaChinhVL", vbTextCompare) = 0 Then Set prj = p: Exit For
    Next p
    On Error GoTo 0
    If prj Is Nothing Then
        DC_ThongBao "Kh" & ChrW(244) & "ng truy c" & ChrW(7853) & "p " & ChrW(273) & ChrW(432) & ChrW(7907) & "c project DiaChinhVL " & ChrW(273) & ChrW(7875) & " t" & ChrW(7841) & "o form " & tenForm & ".", CF_TieuDe, vbExclamation
        Exit Sub
    End If
    src = DC_CAPNHAT & "\" & tenForm & ".txt"
    If Len(Dir$(src)) = 0 Then src = DC_CAPNHAT & "\_danap\" & tenForm & ".txt"
    If Len(Dir$(src)) = 0 Then
        DC_ThongBao "Ch" & ChrW(432) & "a c" & ChrW(243) & " form " & tenForm & " v" & ChrW(224) & " kh" & ChrW(244) & "ng t" & ChrW(236) & "m th" & ChrW(7845) & "y file " & tenForm & ".txt trong th" & ChrW(432) & " m" & ChrW(7909) & "c capnhat.", CF_TieuDe, vbExclamation
        Exit Sub
    End If
    code = DocFileCF(src)
    On Error Resume Next
    Set c = prj.VBComponents(tenForm)
    On Error GoTo Loi
    If c Is Nothing Then
        Set c = prj.VBComponents.Add(3)     ' 3 = UserForm
        c.Name = tenForm
    End If
    With c.CodeModule
        If .CountOfLines > 0 Then .DeleteLines 1, .CountOfLines
        .AddFromString code
    End With
    If InStr(1, src, "\_danap\", vbTextCompare) = 0 Then
        On Error Resume Next
        If Len(Dir$(DC_CAPNHAT & "\_danap", vbDirectory)) = 0 Then MkDir DC_CAPNHAT & "\_danap"
        If Len(Dir$(DC_CAPNHAT & "\_danap\" & tenForm & ".txt")) > 0 Then Kill DC_CAPNHAT & "\_danap\" & tenForm & ".txt"
        Name src As DC_CAPNHAT & "\_danap\" & tenForm & ".txt"
    End If
    On Error Resume Next
    CadInputQueue.SendKeyin "vba save DiaChinhVL"
    On Error GoTo 0
    DC_ThongBao ChrW(272) & ChrW(227) & " t" & ChrW(7841) & "o form " & tenForm & "." & vbCrLf & "B" & ChrW(7845) & "m Ctrl+S (l" & ChrW(432) & "u project) r" & ChrW(7891) & "i m" & ChrW(7903) & " l" & ChrW(7841) & "i m" & ChrW(7909) & "c menu n" & ChrW(224) & "y.", CF_TieuDe
    Exit Sub
Loi:
    DC_ThongBao "L" & ChrW(7895) & "i t" & ChrW(7841) & "o form " & tenForm & ": " & Err.Description, CF_TieuDe, vbCritical
End Sub

Private Function DocFileCF(ByVal path As String) As String
    Dim n As Integer, s As String
    n = FreeFile
    Open path For Binary Access Read As #n
    s = Space$(LOF(n))
    Get #n, , s
    Close #n
    If Left$(s, 3) = Chr$(239) & Chr$(187) & Chr$(191) Then s = Mid$(s, 4)
    DocFileCF = s
End Function

'============================================================
' CHON FILE / THU MUC (Unicode)
'============================================================
Public Function CF_ChonNhieuFile() As Collection
    Dim ofn As CF_OFN, sBuf As String, sFil As String, sTit As String
    Dim kq As New Collection, parts() As String, i As Long, thu As String, p As Long
    Set CF_ChonNhieuFile = kq
    sBuf = String$(65536, vbNullChar)
    sFil = "DGN (*.dgn)" & vbNullChar & "*.dgn" & vbNullChar & "All (*.*)" & vbNullChar & "*.*" & vbNullChar & vbNullChar
    sTit = "Ch" & ChrW(7885) & "n c" & ChrW(225) & "c file b" & ChrW(7843) & "n " & ChrW(273) & ChrW(7891)
    ofn.lStructSize = LenB(ofn)
    ofn.hwndOwner = CF_GetActiveWindow()
    ofn.lpstrFilter = StrPtr(sFil)
    ofn.nFilterIndex = 1
    ofn.lpstrFile = StrPtr(sBuf)
    ofn.nMaxFile = Len(sBuf)
    ofn.lpstrTitle = StrPtr(sTit)
    ofn.flags = &H80000 Or &H200 Or &H1000 Or &H4 Or &H8   ' EXPLORER|MULTI|FILEMUSTEXIST|HIDEREADONLY|NOCHANGEDIR
    If CF_GetOpenFileNameW(ofn) = 0 Then Exit Function
    p = InStr(sBuf, vbNullChar & vbNullChar)
    If p > 0 Then sBuf = Left$(sBuf, p - 1)
    parts = Split(sBuf, vbNullChar)
    If UBound(parts) < 0 Then Exit Function
    If UBound(parts) = 0 Then
        kq.Add parts(0)
    Else
        thu = parts(0)
        If Right$(thu, 1) <> "\" Then thu = thu & "\"
        For i = 1 To UBound(parts)
            If Len(parts(i)) > 0 Then kq.Add thu & parts(i)
        Next i
    End If
End Function

' Chon 1 file (Unicode). loc dang "Mo ta|*.txt;*.csv|Tat ca|*.*"
Public Function CF_ChonMotFile(ByVal loc As String, ByVal tieuDe As String) As String
    Dim ofn As CF_OFN, sBuf As String, sFil As String, sTit As String, p As Long
    sBuf = String$(4096, vbNullChar)
    sFil = Replace(loc, "|", vbNullChar) & vbNullChar & vbNullChar
    sTit = tieuDe
    ofn.lStructSize = LenB(ofn)
    ofn.hwndOwner = CF_GetActiveWindow()
    ofn.lpstrFilter = StrPtr(sFil)
    ofn.nFilterIndex = 1
    ofn.lpstrFile = StrPtr(sBuf)
    ofn.nMaxFile = Len(sBuf)
    ofn.lpstrTitle = StrPtr(sTit)
    ofn.flags = &H80000 Or &H1000 Or &H4 Or &H8
    If CF_GetOpenFileNameW(ofn) = 0 Then Exit Function
    p = InStr(sBuf, vbNullChar)
    If p > 1 Then CF_ChonMotFile = Left$(sBuf, p - 1)
End Function

Public Function CF_ChonThuMuc(ByVal tieuDe As String) As String
    Dim sh As Object, fd As Object
    On Error Resume Next
    Set sh = CreateObject("Shell.Application")
    Set fd = sh.BrowseForFolder(0, tieuDe, &H1 Or &H40, 0)
    If fd Is Nothing Then Exit Function
    CF_ChonThuMuc = fd.Self.path
End Function

' Gom cac file .dgn trong thu muc (deQuy = ca thu muc con)
Public Sub CF_GomFileDgn(ByVal thuMuc As String, ByVal deQuy As Boolean, ByVal kq As Collection)
    Dim fso As Object, fd As Object
    On Error Resume Next
    Set fso = CreateObject("Scripting.FileSystemObject")
    Set fd = fso.GetFolder(thuMuc)
    If fd Is Nothing Then Exit Sub
    GomThuMuc fso, fd, deQuy, kq
End Sub

Private Sub GomThuMuc(ByVal fso As Object, ByVal fd As Object, ByVal deQuy As Boolean, ByVal kq As Collection)
    Dim f As Object, sf As Object
    On Error Resume Next
    For Each f In fd.Files
        If LCase$(fso.GetExtensionName(f.Name)) = "dgn" Then kq.Add f.path
    Next f
    If deQuy Then
        For Each sf In fd.SubFolders
            GomThuMuc fso, sf, True, kq
        Next sf
    End If
End Sub

'============================================================
' XU LY 1 FILE. Tra ve "" neu OK, nguoc lai = mo ta loi.
'   cheDo: 0 = TCVN3->Unicode ; 1 = Unicode->TCVN3
'   lvSo : so level (-1 = tat ca)
'============================================================
Public Function CF_XuLyFile(ByVal path As String, ByVal cheDo As Long, ByVal lvSo As Long, _
                            ByVal saoLuu As Boolean, ByRef soChu As Long) As String
    Dim df As DesignFile, laHienTai As Boolean, m As ModelReference
    Dim fU As Object, fV As Object, fVH As Object
    soChu = 0
    On Error Resume Next
    laHienTai = (StrComp(ActiveDesignFile.FullName, path, vbTextCompare) = 0)
    Err.Clear
    If saoLuu Then
        Dim fso As Object
        Set fso = CreateObject("Scripting.FileSystemObject")
        fso.CopyFile path, path & ".bak", True
        If Err.Number <> 0 Then
            CF_XuLyFile = "Kh" & ChrW(244) & "ng sao l" & ChrW(432) & "u " & ChrW(273) & ChrW(432) & ChrW(7907) & "c (.bak): " & Err.Description
            Exit Function
        End If
    End If

    ' File V7 (dinh dang cu, font 1 byte) khong luu duoc Unicode/TrueType
    ' -> luu thanh file V8 moi "<ten>_unicode.dgn" roi xu ly file moi
    CF_FileMoi = ""
    GhiLog "", True
    GhiLog "FILE " & path & " cheDo=" & cheDo & " lv=" & lvSo
    If LaFileV7(path) Then
        Dim pMoi As String, o As Object
        pMoi = Left$(path, InStrRev(path, ".") - 1) & "_unicode.dgn"
        Err.Clear
        If laHienTai Then
            Set o = ActiveDesignFile
            o.SaveAs pMoi, True, msdDesignFileFormatV8
        Else
            Set o = Application.OpenDesignFileForProgram(path, True)
            o.SaveAs pMoi, True, msdDesignFileFormatV8
            o.Close
            Set o = Nothing
        End If
        If Err.Number <> 0 Or Dir$(pMoi) = "" Then
            CF_XuLyFile = "File V7 (" & ChrW(273) & ChrW(7883) & "nh d" & ChrW(7841) & "ng c" & ChrW(361) & ") kh" & ChrW(244) & "ng chuy" & ChrW(7875) & "n sang V8 " & ChrW(273) & ChrW(432) & ChrW(7907) & "c. M" & ChrW(7903) & " file n" & ChrW(224) & "y r" & ChrW(7891) & "i d" & ChrW(249) & "ng '+ File hi" & ChrW(7879) & "n t" & ChrW(7841) & "i'."
            Exit Function
        End If
        Err.Clear
        path = pMoi
        CF_FileMoi = pMoi
        laHienTai = (StrComp(ActiveDesignFile.FullName, path, vbTextCompare) = 0)
        Err.Clear
    End If

    On Error GoTo Loi
    If laHienTai Then
        Set df = ActiveDesignFile
    Else
        Set df = Application.OpenDesignFileForProgram(path, False)
    End If
    If df Is Nothing Then CF_XuLyFile = "Kh" & ChrW(244) & "ng m" & ChrW(7903) & " " & ChrW(273) & ChrW(432) & ChrW(7907) & "c file": Exit Function

    Set fU = TimFont(df, DC_FONT_VIET)
    Set fV = TimFont(df, FONT_TCVN)
    Set fVH = TimFont(df, FONT_TCVN_H)
    If fVH Is Nothing Then Set fVH = fV
    If cheDo = 0 And fU Is Nothing Then Err.Raise vbObjectError + 1, , "Kh" & ChrW(244) & "ng c" & ChrW(243) & " font " & DC_FONT_VIET
    If cheDo = 1 And fV Is Nothing Then Err.Raise vbObjectError + 2, , "Kh" & ChrW(244) & "ng c" & ChrW(243) & " font " & FONT_TCVN

    For Each m In df.Models
        GhiLog "MODEL " & m.Name
        soChu = soChu + XuLyModel(m, cheDo, lvSo, fU, fV, fVH)
    Next m
    GhiLog "SAVE soChu=" & soChu
    If soChu > 0 Then df.Save
    GhiLog "XONG"
    If Not laHienTai Then df.Close
    Exit Function
Loi:
    CF_XuLyFile = Err.Description
    On Error Resume Next
    If Not laHienTai Then
        If Not df Is Nothing Then df.Close
    End If
End Function

Private Function XuLyModel(ByVal m As ModelReference, ByVal cheDo As Long, ByVal lvSo As Long, _
                           ByVal fU As Object, ByVal fV As Object, ByVal fVH As Object) As Long
    Dim esc As ElementScanCriteria, ee As ElementEnumerator, dS As New Collection, i As Long, el As Element
    On Error Resume Next
    Set esc = New ElementScanCriteria
    esc.ExcludeAllTypes
    esc.IncludeType msdElementTypeText
    esc.IncludeType msdElementTypeTextNode
    Set ee = m.Scan(esc)
    If ee Is Nothing Then Exit Function
    Do While ee.MoveNext
        Set el = ee.Current
        If lvSo < 0 Then
            dS.Add el
        ElseIf DC_LevelSo(el) = lvSo Then
            dS.Add el
        End If
    Loop
    GhiLog "  so phan tu chu: " & dS.Count
    For i = 1 To dS.Count
        Set el = dS.Item(i)
        GhiLog "  #" & i & " type=" & el.Type & " id=" & DLongToString(el.id)
        If el.Type = msdElementTypeTextNode Then
            XuLyModel = XuLyModel + ThayNode(m, el, cheDo, fU, fV, fVH)
        Else
            XuLyModel = XuLyModel + ThayText(m, el, cheDo, fU, fV, fVH)
        End If
    Next i
End Function

' ------------------------------------------------------------
' Cach an toan: KHONG sua font tren phan tu cu (doi font RSC -> TrueType
' tren phan tu co san lam MicroStation treo). Tao phan tu MOI tu dau
' (giong modGanTag.DatTag), chep thuoc tinh, roi ReplaceElement.
' ------------------------------------------------------------
Private Function ThayText(ByVal m As ModelReference, ByVal el As Element, ByVal cheDo As Long, _
                          ByVal fU As Object, ByVal fV As Object, ByVal fVH As Object) As Long
    Dim oT As TextElement, sMoi As String, fMoi As Object, nt As TextElement
    On Error Resume Next
    Set oT = el.AsTextElement
    If oT Is Nothing Then Exit Function
    If Not CanDoi(TenFontAT(oT), oT.Text, cheDo, fU, fV, fVH, sMoi, fMoi) Then Exit Function
    If fMoi Is Nothing Then Exit Function
    GhiLog "    text: tao moi"
    Set nt = TaoText(oT, sMoi, fMoi)
    If nt Is Nothing Then GhiLog "    khong tao duoc": Exit Function
    ChepThuocTinh el, nt
    Err.Clear
    GhiLog "    text: replace"
    m.ReplaceElement el, nt
    If Err.Number = 0 Then ThayText = 1 Else GhiLog "    loi replace: " & Err.Description
End Function

' Text node: tao tung dong thanh chu moi (cung vi tri), them vao, xoa node cu.
Private Function ThayNode(ByVal m As ModelReference, ByVal el As Element, ByVal cheDo As Long, _
                          ByVal fU As Object, ByVal fV As Object, ByVal fVH As Object) As Long
    Dim subs As ElementEnumerator, oT As TextElement, n As Long, i As Long, coDoi As Boolean
    Dim dS As New Collection, txt() As String, sMoi As String, fMoi As Object, fDung As Object, nt As TextElement
    On Error Resume Next
    Set subs = el.AsComplexElement.GetSubElements
    ReDim txt(0 To 0)
    Do While subs.MoveNext
        If subs.Current.Type = msdElementTypeText Then
            Set oT = subs.Current.AsTextElement
            n = n + 1
            ReDim Preserve txt(0 To n)
            dS.Add oT
            txt(n) = oT.Text
            If CanDoi(TenFontAT(oT), oT.Text, cheDo, fU, fV, fVH, sMoi, fMoi) Then
                txt(n) = sMoi: coDoi = True
                If fDung Is Nothing Then Set fDung = fMoi
                If cheDo = 1 And fMoi Is fV Then Set fDung = fV
            End If
        End If
    Loop
    If Not coDoi Or n = 0 Or fDung Is Nothing Then Exit Function
    GhiLog "    node: " & n & " dong -> tach thanh chu"
    For i = 1 To n
        Err.Clear
        Set nt = Nothing
        Set nt = TaoText(dS.Item(i), txt(i), fDung)
        If Not nt Is Nothing Then
            ChepThuocTinh el, nt
            m.AddElement nt
        End If
    Next i
    Err.Clear
    GhiLog "    node: xoa node cu"
    m.RemoveElement el
    If Err.Number = 0 Then ThayNode = 1 Else GhiLog "    loi xoa node: " & Err.Description
End Function

' Tao chu moi (khong mau) cung vi tri/goc/co chu/canh le voi oT, font f
Private Function TaoText(ByVal oT As TextElement, ByVal s As String, ByVal f As Object) As TextElement
    Dim nt As TextElement, ts As TextStyle, h As Double, w As Double, j As Long, org As Point3d, rot As Matrix3d
    On Error Resume Next
    Err.Clear
    h = oT.TextStyle.Height: w = oT.TextStyle.Width: j = oT.TextStyle.Justification
    org = oT.Origin
    rot = oT.Rotation
    If Err.Number <> 0 Then GhiLog "    loi doc: " & Err.Description: Err.Clear
    Set nt = CreateTextElement1(Nothing, s, org, rot)
    If nt Is Nothing Then Exit Function
    Set ts = nt.TextStyle
    Set ts.Font = f
    If Err.Number <> 0 Then Err.Clear: ts.Font = f
    If h > 0 Then ts.Height = h
    If w > 0 Then ts.Width = w
    ts.Justification = j
    Set nt.TextStyle = ts
    If Err.Number <> 0 Then Err.Clear: nt.TextStyle = ts
    Set TaoText = nt
End Function

Private Sub ChepThuocTinh(ByVal cu As Element, ByVal moi As Element)
    On Error Resume Next
    Set moi.Level = cu.Level
    moi.color = cu.color
    moi.LineWeight = cu.LineWeight
    Set moi.LineStyle = cu.LineStyle
    moi.GraphicGroup = cu.GraphicGroup
    moi.Class = cu.Class
End Sub

' Quyet dinh co doi khong; tra ve chuoi moi + font moi
Private Function CanDoi(ByVal tenFont As String, ByVal s As String, ByVal cheDo As Long, _
                        ByVal fU As Object, ByVal fV As Object, ByVal fVH As Object, _
                        ByRef sMoi As String, ByRef fMoi As Object) As Boolean
    Dim fn As String, laVn As Boolean, hoa As Boolean
    fn = LCase$(Trim$(tenFont))
    laVn = (Left$(fn, 2) = "vn" Or Left$(fn, 3) = ".vn")
    If cheDo = 0 Then
        If laVn Then
            sMoi = TcvnSangUni(s)
            If Right$(fn, 1) = "h" Then sMoi = UCase$(sMoi)      ' .VnTimeH, .VnArialH: font chu hoa
        ElseIf (Len(fn) = 0 Or Not FontUnicode(fn)) And LaTcvn3(s) Then
            ' font so (V7 / RSC: 160, 155...) nhung noi dung la ma TCVN3
            sMoi = TcvnSangUni(s)
        Else
            Exit Function
        End If
        Set fMoi = fU
        CanDoi = True
    Else
        If laVn Then Exit Function
        If Not CoKyTuViet(s) Then Exit Function
        sMoi = UnicodeSangTcvn3(s, hoa)
        If hoa Then Set fMoi = fVH Else Set fMoi = fV
        CanDoi = True
    End If
End Function

' Ten font an toan ("" neu font khong co trong bang font, vd font so 160 cua file V7)
Private Function TenFontAT(ByVal oT As TextElement) As String
    Dim f As Object
    On Error Resume Next
    Set f = oT.TextStyle.Font
    If Not f Is Nothing Then TenFontAT = f.Name
End Function

' Nhat ky de tim cho bi treo: C:\DiaChinhVL\convertfont_log.txt (dong file moi dong)
Private Sub GhiLog(ByVal s As String, Optional ByVal moi As Boolean = False)
    Dim f As Integer
    On Error Resume Next
    f = FreeFile
    If moi Then
        Open "C:\DiaChinhVL\convertfont_log.txt" For Output As #f
    Else
        Open "C:\DiaChinhVL\convertfont_log.txt" For Append As #f
        Print #f, Format$(Now, "hh:nn:ss") & " " & s
    End If
    Close #f
End Sub

' Font TrueType Unicode (hoac VNI) -> khong coi la TCVN3
Private Function FontUnicode(ByVal fn As String) As Boolean
    Select Case fn
        Case "times new roman", "arial", "tahoma", "calibri", "cambria", "verdana", "segoe ui", "courier new", "arial unicode ms"
            FontUnicode = True
    End Select
    If Left$(fn, 3) = "vni" Then FontUnicode = True
End Function

' Doi ky tu da bi giai ma theo 1252/1258 ve lai byte goc. ok = False neu co ky tu Unicode that.
Private Function ChuoiByte(ByVal s As String, ByRef ok As Boolean) As String
    Dim i As Long, c As Long, r As String
    NapRev
    ok = True
    For i = 1 To Len(s)
        c = AscW(Mid$(s, i, 1)) And &HFFFF&
        If c < 256 Then
            r = r & ChrW(c)
        ElseIf mByte.Exists(c) Then
            r = r & ChrW(mByte(c))
        Else
            ok = False
            r = r & ChrW(c)
        End If
    Next i
    ChuoiByte = r
End Function

' Chuoi 8-bit co ky tu Viet ma TCVN3
Private Function LaTcvn3(ByVal s As String) As Boolean
    Dim b As String, ok As Boolean, i As Long, c As Long
    b = ChuoiByte(s, ok)
    If Not ok Then Exit Function
    For i = 1 To Len(b)
        c = AscW(Mid$(b, i, 1))
        If c >= &HA1 Then
            If mFwd.Exists(c) Then LaTcvn3 = True: Exit Function
        End If
    Next i
End Function

Private Function TcvnSangUni(ByVal s As String) As String
    Dim b As String, ok As Boolean, i As Long, c As Long, r As String
    b = ChuoiByte(s, ok)
    For i = 1 To Len(b)
        c = AscW(Mid$(b, i, 1)) And &HFFFF&
        If mFwd.Exists(c) Then r = r & ChrW(mFwd(c)) Else r = r & ChrW(c)
    Next i
    TcvnSangUni = r
End Function

' DGN V7: khong phai file OLE (V8 bat dau D0 CF 11 E0), phan tu dau la TCB (type 9)
Private Function LaFileV7(ByVal path As String) As Boolean
    Dim f As Integer, b(0 To 1) As Byte
    On Error GoTo Thoat
    f = FreeFile
    Open path For Binary Access Read Shared As #f
    Get #f, 1, b
    Close #f
    LaFileV7 = (b(0) <> &HD0 And (b(1) And &H7F) = 9)
    Exit Function
Thoat:
    On Error Resume Next
    Close #f
End Function

Private Function CoKyTuViet(ByVal s As String) As Boolean
    Dim i As Long
    For i = 1 To Len(s)
        If (AscW(Mid$(s, i, 1)) And &HFFFF&) >= 128 Then CoKyTuViet = True: Exit Function
    Next i
End Function

' (DoiText/DoiNode cu da bo: sua font tren phan tu co san lam MicroStation treo)

'============================================================
' Unicode -> TCVN3. hoa = True khi chuoi la chu HOA co dau
'   (khi do tra ve chu thuong de dung font .VnTimeH)
'============================================================
Private Function UnicodeSangTcvn3(ByVal s As String, ByRef hoa As Boolean) As String
    Dim i As Long, c As Long, ch As String, r As String, coHoaDau As Boolean
    NapRev
    hoa = False
    For i = 1 To Len(s)
        ch = Mid$(s, i, 1)
        c = AscW(ch) And &HFFFF&
        If c >= 128 Then
            If Not mRev.Exists(c) Then
                If mRev.Exists(AscW(LCase$(ch)) And &HFFFF&) Then coHoaDau = True
            End If
        End If
    Next i
    If coHoaDau And s = UCase$(s) Then hoa = True: s = LCase$(s)
    For i = 1 To Len(s)
        ch = Mid$(s, i, 1)
        c = AscW(ch) And &HFFFF&
        If c >= 128 Then
            If mRev.Exists(c) Then
                r = r & ChrW(mRev(c))
            ElseIf mRev.Exists(AscW(LCase$(ch)) And &HFFFF&) Then
                r = r & ChrW(mRev(AscW(LCase$(ch)) And &HFFFF&))
            Else
                r = r & ch
            End If
        Else
            r = r & ch
        End If
    Next i
    UnicodeSangTcvn3 = r
End Function

Private Sub NapRev()
    Dim a() As String, i As Long, b As Long, u As Long
    If Not mRev Is Nothing Then Exit Sub
    Set mRev = CreateObject("Scripting.Dictionary")
    Set mFwd = CreateObject("Scripting.Dictionary")
    Set mByte = CreateObject("Scripting.Dictionary")
    a = Split(TCVN_MAP, ",")
    For i = LBound(a) To UBound(a)
        b = CLng("&H" & Left$(a(i), 2))
        u = CLng("&H" & Mid$(a(i), 3, 4))
        If Not mRev.Exists(u) Then mRev.Add u, b
        If Not mFwd.Exists(b) Then mFwd.Add b, u
    Next i
    a = Split(BYTE_MAP, ",")
    For i = LBound(a) To UBound(a)
        u = CLng("&H" & Left$(a(i), 4))
        b = CLng("&H" & Mid$(a(i), 5, 2))
        If Not mByte.Exists(u) Then mByte.Add u, b
    Next i
End Sub

Private Function TimFont(ByVal df As DesignFile, ByVal ten As String) As Object
    Dim fs As Object, f As Object, i As Long
    On Error Resume Next
    Set fs = df.Fonts
    If fs Is Nothing Then Set fs = ActiveDesignFile.Fonts
    For Each f In fs
        If StrComp(f.Name, ten, vbTextCompare) = 0 Then Set TimFont = f: Exit Function
    Next f
    For i = 0 To 1023
        Set f = Nothing
        Set f = fs.Item(i)
        If Not f Is Nothing Then
            If StrComp(f.Name, ten, vbTextCompare) = 0 Then Set TimFont = f: Exit Function
        End If
    Next i
End Function

Attribute VB_Name = "modCuonChuot"
'============================================================
' modCuonChuot - LAN CON CHUOT de cuon ListBox tren form (MSForms khong tu ho tro)
'   Moi form: Set mCuon = DC_GanCuon(lst, Me) sau khi tao ListBox ;
'             UserForm_Terminate -> DC_CuonTat
'   Hook chuot (WH_MOUSE_LL) chi bat khi chuot vao ListBox, tu go khi chuot
'   ra khoi form (khong an mat cuon chuot de zoom trong MicroStation).
'============================================================
Option Explicit

Private Type POINTAPI
    x As Long
    y As Long
End Type

Private Declare Function SetWindowsHookEx Lib "user32" Alias "SetWindowsHookExA" (ByVal idHook As Long, ByVal lpfn As Long, ByVal hmod As Long, ByVal dwThreadId As Long) As Long
Private Declare Function CallNextHookEx Lib "user32" (ByVal hHook As Long, ByVal nCode As Long, ByVal wParam As Long, ByVal lParam As Long) As Long
Private Declare Function UnhookWindowsHookEx Lib "user32" (ByVal hHook As Long) As Long
Private Declare Function GetModuleHandle Lib "kernel32" Alias "GetModuleHandleA" (ByVal lpModuleName As String) As Long
Private Declare Sub CopyMemory Lib "kernel32" Alias "RtlMoveMemory" (Destination As Any, ByVal Source As Long, ByVal Length As Long)
Private Declare Function WindowFromPoint Lib "user32" (ByVal xPoint As Long, ByVal yPoint As Long) As Long
Private Declare Function GetAncestor Lib "user32" (ByVal hwnd As Long, ByVal gaFlags As Long) As Long
Private Declare Function FindWindow Lib "user32" Alias "FindWindowA" (ByVal lpClassName As String, ByVal lpWindowName As String) As Long

Private Const WH_MOUSE_LL As Long = 14
Private Const WM_MOUSEWHEEL As Long = &H20A
Private Const GA_ROOT As Long = 2

Private mHook As Long
Private mLst As Object
Private mHwnd As Long

' Gan cuon chuot cho 1 ListBox cua form. Giu doi tuong tra ve trong form.
Public Function DC_GanCuon(ByVal lst As Object, ByVal frm As Object) As Object
    Dim c As clsCuonList
    On Error Resume Next
    Set c = New clsCuonList
    Set c.lst = lst
    Set c.Form = frm
    Set DC_GanCuon = c
End Function

' Goi khi chuot di vao ListBox
Public Sub DC_CuonBat(ByVal lst As Object, ByVal frm As Object)
    On Error Resume Next
    Set mLst = lst
    If mHook <> 0 Then Exit Sub
    mHwnd = FindWindow("ThunderDFrame", frm.Caption)
    If mHwnd = 0 Then mHwnd = FindWindow(vbNullString, frm.Caption)
    If mHwnd = 0 Then Exit Sub
    mHook = SetWindowsHookEx(WH_MOUSE_LL, AddressOf CuonProc, GetModuleHandle(vbNullString), 0)
End Sub

' Go hook (dong form / chuot ra ngoai form)
Public Sub DC_CuonTat()
    On Error Resume Next
    If mHook <> 0 Then UnhookWindowsHookEx mHook
    mHook = 0
    Set mLst = Nothing
End Sub

Private Function CuonProc(ByVal nCode As Long, ByVal wParam As Long, ByVal lParam As Long) As Long
    Dim pt As POINTAPI, md As Long, h As Long, hK As Long
    On Error Resume Next
    hK = mHook
    If nCode = 0 And wParam = WM_MOUSEWHEEL Then
        CopyMemory pt, lParam, 8
        CopyMemory md, lParam + 8, 4
        h = WindowFromPoint(pt.x, pt.y)
        If h <> 0 Then h = GetAncestor(h, GA_ROOT)
        If h = mHwnd And mHwnd <> 0 And Not mLst Is Nothing Then
            CuonList mLst, md
            CuonProc = 1
            Exit Function
        End If
        ' chuot da ra ngoai form -> go hook, tra lai cuon chuot cho MicroStation
        CuonProc = CallNextHookEx(hK, nCode, wParam, lParam)
        DC_CuonTat
        Exit Function
    End If
    CuonProc = CallNextHookEx(hK, nCode, wParam, lParam)
End Function

Private Sub CuonList(ByVal lst As Object, ByVal md As Long)
    Dim d As Long, b As Long, ti As Long, n As Long
    On Error Resume Next
    d = Fix(md / 65536#)
    If d = 0 Then Exit Sub
    b = Abs(d) \ 120: If b < 1 Then b = 1
    n = lst.ListCount
    If n = 0 Then Exit Sub
    ti = lst.TopIndex - Sgn(d) * 3 * b
    If ti < 0 Then ti = 0
    If ti > n - 1 Then ti = n - 1
    lst.TopIndex = ti
End Sub

Attribute VB_Name = "modDiemMia"
'============================================================
' modDiemMia - Diem mia toa do (trien diem theo danh sach, kieu LandMap)
'   Form frmDiemMia (tu tao): Tep diem mia -> Xem du lieu -> Hien diem mia.
'   Du lieu nap vao mang trong module; X = Bac (y ban ve), Y = Dong (x ban ve).
'============================================================
Option Explicit

Public DM_N As Long
Public DM_Ten() As String, DM_Ma() As String, DM_H() As String
Public DM_X() As Double, DM_Y() As Double

Private mFont As Object

Public Sub DC_MoDiemMia()
    DC_MoFormTuTao "frmDiemMia"
End Sub

Public Function DM_TenCot() As Variant
    DM_TenCot = Array("T" & ChrW(234) & "n " & ChrW(273) & "i" & ChrW(7875) & "m", "X", "Y", "H", "M" & ChrW(227) & " " & ChrW(273) & "i" & ChrW(7875) & "m", "(b" & ChrW(7887) & " qua)")
End Function

' Doc 1 file. cot(0..4) = loai cot (0 Ten,1 X,2 Y,3 H,4 Ma,5 bo qua); sep = cac ky tu phan cach
' (chuoi, " " = dau cach). Tra ve so diem them; nBo = so dong bo qua.
Public Function DM_DocFile(ByVal f As String, ByRef cot() As Long, ByVal sep As String, ByRef nBo As Long) As Long
    Dim txt As String, Dong() As String, i As Long, p() As String, j As Long
    Dim ten As String, ma As String, h As String, sx As String, sy As String, ok As Boolean
    txt = DocChuDM(f)
    If Len(txt) = 0 Then Exit Function
    Dong = Split(Replace(txt, vbCr, ""), vbLf)
    For i = 0 To UBound(Dong)
        If Len(Trim$(Dong(i))) > 0 Then
            p = TachDM(Dong(i), sep)
            ten = "": ma = "": h = "": sx = "": sy = ""
            For j = 0 To 4
                If j <= UBound(p) Then
                    Select Case cot(j)
                        Case 0: ten = p(j)
                        Case 1: sx = p(j)
                        Case 2: sy = p(j)
                        Case 3: h = p(j)
                        Case 4: ma = p(j)
                    End Select
                End If
            Next j
            ok = LaSoDM(sx) And LaSoDM(sy)
            If ok Then
                DM_N = DM_N + 1
                If DM_N = 1 Then
                    ReDim DM_Ten(1 To 64): ReDim DM_Ma(1 To 64): ReDim DM_H(1 To 64)
                    ReDim DM_X(1 To 64): ReDim DM_Y(1 To 64)
                ElseIf DM_N > UBound(DM_X) Then
                    ReDim Preserve DM_Ten(1 To DM_N * 2): ReDim Preserve DM_Ma(1 To DM_N * 2): ReDim Preserve DM_H(1 To DM_N * 2)
                    ReDim Preserve DM_X(1 To DM_N * 2): ReDim Preserve DM_Y(1 To DM_N * 2)
                End If
                DM_Ten(DM_N) = ten: DM_Ma(DM_N) = ma: DM_H(DM_N) = h
                DM_X(DM_N) = SoDM(sx): DM_Y(DM_N) = SoDM(sy)
                DM_DocFile = DM_DocFile + 1
            Else
                nBo = nBo + 1
            End If
        End If
    Next i
End Function

Public Sub DM_XoaDuLieu()
    DM_N = 0
    Erase DM_Ten, DM_Ma, DM_H, DM_X, DM_Y
End Sub

' Tu nhan dang cot tu vai dong dau: tra ve chuoi 5 so (vd "0,1,2,3,5")
Public Function DM_DoanCot(ByVal f As String, ByVal sep As String) As String
    Dim txt As String, Dong() As String, i As Long, p() As String, j As Long, n As Long
    Dim lon(0 To 9) As Long, le(0 To 9) As Long, so(0 To 9) As Long, kq(0 To 4) As Long, v As Double
    txt = DocChuDM(f)
    If Len(txt) = 0 Then Exit Function
    Dong = Split(Replace(txt, vbCr, ""), vbLf)
    For i = 0 To UBound(Dong)
        If n >= 10 Then Exit For
        If Len(Trim$(Dong(i))) > 0 Then
            p = TachDM(Dong(i), sep)
            If UBound(p) >= 2 Then
                n = n + 1
                For j = 0 To UBound(p)
                    If j > 9 Then Exit For
                    If LaSoDM(p(j)) Then
                        so(j) = so(j) + 1
                        v = SoDM(p(j))
                        If Abs(v) > 100000 Then lon(j) = lon(j) + 1
                        If InStr(p(j), ".") > 0 Or InStr(p(j), ",") > 0 Then le(j) = le(j) + 1
                    End If
                Next j
            End If
        End If
    Next i
    If n = 0 Then Exit Function
    ' 2 cot so lon lien tiep = X (Bac, lon hon) / Y
    Dim cx As Long, cy As Long, ch As Long, cM As Long
    cx = -1: cy = -1: ch = -1: cM = -1
    For j = 0 To 8
        If lon(j) * 2 > n And lon(j + 1) * 2 > n Then cx = j: cy = j + 1: Exit For
    Next j
    If cx < 0 Then Exit Function
    For j = 0 To 4
        kq(j) = 5
    Next j
    If cx <= 4 Then kq(cx) = 1
    If cy <= 4 Then kq(cy) = 2
    If cx > 0 Then kq(0) = 0                          ' ten diem o cot dau
    If cx = 2 Then kq(1) = 4                          ' Ten, Ma, X, Y
    If cy + 1 <= 4 Then If so(cy + 1) * 2 > n And le(cy + 1) * 2 > n Then kq(cy + 1) = 3: ch = cy + 1
    If ch > 0 And ch + 1 <= 4 Then If kq(ch + 1) = 5 Then kq(ch + 1) = 4
    DM_DoanCot = kq(0) & "," & kq(1) & "," & kq(2) & "," & kq(3) & "," & kq(4)
End Function

' Ve diem: lv, co chu (m); hien ten / H / ma; kieu ky hieu 0 = vong tron, 1 = dau cong
Public Function DM_Ve(ByVal lvSo As Long, ByVal cao As Double, ByVal coTen As Boolean, ByVal coH As Boolean, _
                      ByVal coMa As Boolean, ByVal kieu As Long, ByVal soLeH As Long) As Long
    Dim i As Long, lv As Level, r As Double, x As Double, y As Double, d As Double
    Dim x1 As Double, y1 As Double, x2 As Double, y2 As Double, s As String
    If DM_N = 0 Then Exit Function
    Set lv = DC_LevelTheoSo(lvSo)
    r = cao * 0.25
    For i = 1 To DM_N
        x = DM_Y(i): y = DM_X(i)                ' Y = Dong -> x ban ve
        If kieu = 1 Then
            VeDoan x - r, y, x + r, y, lv
            VeDoan x, y - r, x, y + r, lv
        Else
            VeVongDM x, y, r, lv
        End If
        If coTen And Len(DM_Ten(i)) > 0 Then VeChuDM x + cao * 0.4, y + cao * 0.15, DM_Ten(i), cao, lv, msdTextJustificationLeftBottom
        s = ""
        If coH And Len(DM_H(i)) > 0 Then s = Format$(SoDM(DM_H(i)), IIf(soLeH > 0, "0." & String$(soLeH, "0"), "0"))
        If coMa And Len(DM_Ma(i)) > 0 Then s = s & IIf(Len(s) > 0, "  ", "") & DM_Ma(i)
        If Len(s) > 0 Then VeChuDM x + cao * 0.4, y - cao * 0.15, s, cao * 0.8, lv, msdTextJustificationLeftTop
        If i = 1 Then
            x1 = x: x2 = x: y1 = y: y2 = y
        Else
            If x < x1 Then x1 = x
            If x > x2 Then x2 = x
            If y < y1 Then y1 = y
            If y > y2 Then y2 = y
        End If
        DM_Ve = DM_Ve + 1
    Next i
    d = x2 - x1: If y2 - y1 > d Then d = y2 - y1
    If d < 20 Then d = 20
    DC_ZoomVung (x1 + x2) / 2 - d * 0.6, (y1 + y2) / 2 - d * 0.6, (x1 + x2) / 2 + d * 0.6, (y1 + y2) / 2 + d * 0.6
End Function

'------------------------------------------------------------ dung chung
Public Function TachDM(ByVal s As String, ByVal sep As String) As String()
    Dim t As String, a() As String, i As Long, kq() As String, n As Long, c As String
    t = s
    If Len(t) > 0 Then
        If AscW(Left$(t, 1)) = &HFEFF Then t = Mid$(t, 2)
    End If
    If InStr(sep, " ") > 0 Then
        t = Replace(t, vbTab, IIf(InStr(sep, vbTab) > 0, Chr$(1), " "))
        t = Trim$(t)
        Do While InStr(t, "  ") > 0: t = Replace(t, "  ", " "): Loop
    End If
    For i = 1 To Len(sep)
        c = Mid$(sep, i, 1)
        t = Replace(t, c, Chr$(1))
    Next i
    a = Split(t, Chr$(1))
    ReDim kq(0 To UBound(a))
    For i = 0 To UBound(a)
        If InStr(sep, " ") > 0 And Len(Trim$(a(i))) = 0 Then GoTo tiep
        kq(n) = Trim$(a(i)): n = n + 1
tiep:
    Next i
    If n = 0 Then ReDim kq(0 To 0) Else ReDim Preserve kq(0 To n - 1)
    TachDM = kq
End Function

Private Function LaSoDM(ByVal s As String) As Boolean
    Dim t As String
    t = Replace(Trim$(s), ",", ".")
    If Len(t) = 0 Then Exit Function
    LaSoDM = (t Like "*#*") And Not (t Like "*[!0-9.+-]*")
End Function

Private Function SoDM(ByVal s As String) As Double
    SoDM = val(Replace(Trim$(s), ",", "."))
End Function

Public Function DocChuDM(ByVal f As String) As String
    Dim st As Object
    On Error Resume Next
    Set st = CreateObject("ADODB.Stream")
    st.Type = 2: st.Charset = "utf-8": st.Open
    st.LoadFromFile f
    DocChuDM = st.ReadText(-1)
    st.Close
    If Len(DocChuDM) > 0 Then
        If AscW(Left$(DocChuDM, 1)) = &HFEFF Then DocChuDM = Mid$(DocChuDM, 2)
    End If
End Function

Private Function FontDM() As Object
    Dim f As Object
    If Not mFont Is Nothing Then Set FontDM = mFont: Exit Function
    On Error Resume Next
    For Each f In ActiveDesignFile.Fonts
        If StrComp(f.Name, DC_FONT_VIET, vbTextCompare) = 0 Then Set mFont = f: Exit For
    Next f
    Set FontDM = mFont
End Function

Private Sub VeChuDM(ByVal x As Double, ByVal y As Double, ByVal s As String, ByVal cao As Double, _
                    ByVal lv As Level, ByVal canh As Long)
    Dim t As TextElement, ts As TextStyle, f As Object
    On Error Resume Next
    Set t = CreateTextElement1(Nothing, s, Point3dFromXYZ(x, y, 0#), Matrix3dIdentity)
    If t Is Nothing Then Exit Sub
    Set ts = t.TextStyle
    ts.Height = cao: ts.Width = cao
    ts.Justification = canh
    Set f = FontDM()
    If Not f Is Nothing Then Set ts.Font = f
    Set t.TextStyle = ts
    If Err.Number <> 0 Then Err.Clear: t.TextStyle = ts
    If Not lv Is Nothing Then Set t.Level = lv
    t.LineWeight = 0
    ActiveModelReference.AddElement t
End Sub

Private Sub VeVongDM(ByVal x As Double, ByVal y As Double, ByVal r As Double, ByVal lv As Level)
    Dim e As EllipseElement
    On Error Resume Next
    Set e = CreateEllipseElement2(Nothing, Point3dFromXYZ(x, y, 0#), r, r, Matrix3dIdentity)
    If e Is Nothing Then Exit Sub
    If Not lv Is Nothing Then Set e.Level = lv
    e.LineWeight = 0
    ActiveModelReference.AddElement e
End Sub

Private Sub VeDoan(ByVal ax As Double, ByVal ay As Double, ByVal bx As Double, ByVal by As Double, ByVal lv As Level)
    Dim e As LineElement
    On Error Resume Next
    Set e = CreateLineElement2(Nothing, Point3dFromXYZ(ax, ay, 0#), Point3dFromXYZ(bx, by, 0#))
    If e Is Nothing Then Exit Sub
    If Not lv Is Nothing Then Set e.Level = lv
    e.LineWeight = 0
    ActiveModelReference.AddElement e
End Sub

Attribute VB_Name = "modDoc"
Option Explicit

'============================================================
' modDoc - Doc ranh tu DGN & ve len ban do (MicroStation V8i)
' Port tu DiaChinhVL_GUI.py: lay_cac_doan, ve_line, ve_tam,
'                            ve_danh_dau_loi + 2 lenh menu.
'
' Dung bo doi tuong MicroStationDGN (COM) cua V8i:
'   ElementScanCriteria + ActiveModelReference.Scan -> ElementEnumerator
'   Current.AsLineElement.GetVertices() -> Point3d()
'   CreateLineElement2(Nothing, p1, p2) + AddElement
'============================================================


'============================================================
' LAY CAC DOAN RANH TU MODEL DANG MO
'   snap      : dung vua de loc doan qua ngan
'   levelRanh : "" = doc tat ca line/linestring moi level;
'               ten level (vd "Level 10") = chi doc level do
'   Tra ve Collection cac Seg (Double 0..3). Bounding box tra ve ByRef.
'============================================================
' Tim Level theo TEN ("Level 10") hoac theo SO (10). Tra Nothing neu khong co.
Private Function TimLevel(ByVal ten As String) As Level
    On Error Resume Next
    Set TimLevel = ActiveModelReference.Levels(Trim$(ten))   ' 1) thu theo ten
    On Error GoTo 0
    If Not TimLevel Is Nothing Then Exit Function
    ' 2) lay chu so trong chuoi -> tim theo Level.Number
    Dim s As String, i As Long, c As String
    For i = 1 To Len(ten)
        c = Mid$(ten, i, 1)
        If c >= "0" And c <= "9" Then s = s & c
    Next i
    If Len(s) = 0 Then Exit Function
    Dim num As Long: num = CLng(s)
    Dim L As Level
    On Error Resume Next
    For Each L In ActiveModelReference.Levels
        If L.Number = num Then Set TimLevel = L: Exit For
    Next L
    On Error GoTo 0
End Function

' So level tu chuoi ("Level 10" hoac "10" -> 10). "" / khong co so -> -1 (tat ca).
Private Function SoLevel(ByVal ten As String) As Long
    Dim s As String, i As Long, c As String
    If Len(Trim$(ten)) = 0 Then SoLevel = -1: Exit Function
    For i = 1 To Len(ten)
        c = Mid$(ten, i, 1)
        If c >= "0" And c <= "9" Then s = s & c
    Next i
    If Len(s) = 0 Then SoLevel = -1 Else SoLevel = CLng(s)
End Function

' Kiem tra mau c co nam trong danh sach mauCSV (vd "0,5"). "" = nhan moi mau.
Private Function MauKhop(ByVal c As Long, ByVal mauCSV As String) As Boolean
    If Len(Trim$(mauCSV)) = 0 Then MauKhop = True: Exit Function
    Dim a() As String, i As Long
    a = Split(mauCSV, ",")
    For i = LBound(a) To UBound(a)
        If Len(Trim$(a(i))) > 0 Then
            If CLng(val(a(i))) = c Then MauKhop = True: Exit Function
        End If
    Next i
    MauKhop = False
End Function

' Them cac doan tu mang dinh pts() vao segs + cap nhat bbox.
' khepKin = True -> them them doan noi dinh cuoi ve dinh dau (cho Shape/ComplexShape).
Private Sub ThemDinhVaoSegs(ByRef pts() As Point3d, ByVal snap As Double, _
                            ByVal segs As Collection, ByRef first As Boolean, _
                            ByRef minX As Double, ByRef minY As Double, _
                            ByRef maxX As Double, ByRef maxY As Double, _
                            ByVal khepKin As Boolean)
    Dim i As Long, dx As Double, dy As Double, lo As Long, hi As Long
    On Error GoTo Thoat
    lo = LBound(pts): hi = UBound(pts)
    If hi <= lo Then Exit Sub
    If Not DC_DinhHopLe(pts) Then Exit Sub        ' SUA 08/11: bo net hong toa do NaN
    For i = lo To hi
        If first Then
            minX = pts(i).x: maxX = pts(i).x: minY = pts(i).y: maxY = pts(i).y: first = False
        Else
            If pts(i).x < minX Then minX = pts(i).x
            If pts(i).x > maxX Then maxX = pts(i).x
            If pts(i).y < minY Then minY = pts(i).y
            If pts(i).y > maxY Then maxY = pts(i).y
        End If
    Next i
    For i = lo To hi - 1
        dx = pts(i + 1).x - pts(i).x: dy = pts(i + 1).y - pts(i).y
        If Sqr(dx * dx + dy * dy) > snap Then segs.Add NewSeg(pts(i).x, pts(i).y, pts(i + 1).x, pts(i + 1).y)
    Next i
    If khepKin Then
        dx = pts(lo).x - pts(hi).x: dy = pts(lo).y - pts(hi).y
        If Sqr(dx * dx + dy * dy) > snap Then segs.Add NewSeg(pts(hi).x, pts(hi).y, pts(lo).x, pts(lo).y)
    End If
Thoat:
End Sub

Public Function LayCacDoan(ByVal snap As Double, ByVal levelRanh As String, _
                           ByRef minX As Double, ByRef minY As Double, _
                           ByRef maxX As Double, ByRef maxY As Double, _
                           Optional ByVal mauCSV As String = "") As Collection
    Dim segs As New Collection
    Dim esc As ElementScanCriteria
    Set esc = New ElementScanCriteria
    esc.ExcludeAllTypes
    esc.IncludeType msdElementTypeLine
    esc.IncludeType msdElementTypeLineString
    esc.IncludeType msdElementTypeShape
    esc.IncludeType msdElementTypeComplexString    ' duong phuc (complex chain)
    esc.IncludeType msdElementTypeComplexShape

    ' Loc theo SO LEVEL doc THANG tren tung doi tuong. lvNum = -1 -> doc tat ca.
    Dim lvNum As Long
    lvNum = SoLevel(levelRanh)

    Dim ee As ElementEnumerator
    Set ee = ActiveModelReference.Scan(esc)

    Dim first As Boolean: first = True
    Dim pts() As Point3d
    Dim el As Element, sub_ As Element, subs As ElementEnumerator
    Dim okLv As Boolean, okMau As Boolean, tp As Long

    Do While ee.MoveNext
        Set el = ee.Current
        okLv = (lvNum < 0)
        okMau = True
        On Error Resume Next
        If Not okLv Then okLv = (el.Level.Number = lvNum)
        okMau = MauKhop(el.color, mauCSV)
        On Error GoTo 0
        If okLv And okMau Then
            Select Case el.Type
                Case msdElementTypeLine, msdElementTypeLineString
                    On Error Resume Next
                    pts = el.AsLineElement.GetVertices()
                    On Error GoTo 0
                    ThemDinhVaoSegs pts, snap, segs, first, minX, minY, maxX, maxY, False
                Case msdElementTypeShape
                    On Error Resume Next
                    pts = el.AsShapeElement.GetVertices()
                    On Error GoTo 0
                    ThemDinhVaoSegs pts, snap, segs, first, minX, minY, maxX, maxY, True
                Case msdElementTypeComplexString, msdElementTypeComplexShape
                    Set subs = Nothing
                    On Error Resume Next
                    If el.Type = msdElementTypeComplexString Then
                        Set subs = el.AsComplexStringElement.GetSubElements
                    Else
                        Set subs = el.AsComplexShapeElement.GetSubElements
                    End If
                    On Error GoTo 0
                    If Not subs Is Nothing Then
                        Do While subs.MoveNext
                            Set sub_ = subs.Current
                            tp = sub_.Type
                            If tp = msdElementTypeLine Or tp = msdElementTypeLineString Then
                                On Error Resume Next
                                pts = sub_.AsLineElement.GetVertices()
                                On Error GoTo 0
                                ThemDinhVaoSegs pts, snap, segs, first, minX, minY, maxX, maxY, False
                            ElseIf tp = msdElementTypeShape Then
                                On Error Resume Next
                                pts = sub_.AsShapeElement.GetVertices()
                                On Error GoTo 0
                                ThemDinhVaoSegs pts, snap, segs, first, minX, minY, maxX, maxY, True
                            End If
                        Loop
                    End If
            End Select
        End If
        Set el = Nothing
    Loop

    Set LayCacDoan = segs
End Function


'============================================================
' VE PRIMITIVE
'============================================================

' CHAN DOAN: dem so Line/LineString theo tung Level.Number + theo mau.
' Chay: Tools > Macros > DC_ChanDoanLevel. Cho biet ranh thua nam level nao / mau gi.
Public Sub DC_ChanDoanLevel()
    Dim esc As ElementScanCriteria
    Set esc = New ElementScanCriteria
    esc.ExcludeAllTypes
    esc.IncludeType msdElementTypeLine
    esc.IncludeType msdElementTypeLineString
    Dim ee As ElementEnumerator
    Set ee = ActiveModelReference.Scan(esc)
    Dim cntLv(0 To 255) As Long, ln As Long, mxLv As Long
    Dim d As Object
    Set d = CreateObject("Scripting.Dictionary")   ' key = lv & "|" & mau -> count
    Do While ee.MoveNext
        ln = -1
        On Error Resume Next
        ln = ee.Current.Level.Number
        On Error GoTo 0
        Dim mau As Long: mau = -1
        On Error Resume Next
        mau = ee.Current.color
        On Error GoTo 0
        If ln >= 0 And ln <= 255 Then
            cntLv(ln) = cntLv(ln) + 1
            If ln > mxLv Then mxLv = ln
        End If
        Dim key As String: key = ln & "|" & mau
        If d.Exists(key) Then d(key) = d(key) + 1 Else d.Add key, 1
    Loop
    Dim s As String, i As Long
    s = "SO LINE THEO LEVEL:" & vbCrLf
    For i = 0 To mxLv
        If cntLv(i) > 0 Then s = s & "  Level " & i & " : " & cntLv(i) & vbCrLf
    Next i
    s = s & vbCrLf & "CHI TIET Level|Mau : so luong" & vbCrLf
    Dim kk As Variant
    For Each kk In d.Keys
        s = s & "  " & kk & " : " & d(kk) & vbCrLf
    Next kk
    MsgBox s, vbInformation, "Chan doan level/mau"
End Sub

' Ve mot doan thang. color = -1 nghia la giu mau/level dang active.
Public Sub VeLine(ByVal ax As Double, ByVal ay As Double, _
                  ByVal bx As Double, ByVal by As Double, _
                  Optional ByVal color As Long = -1)
    Dim p1 As Point3d, p2 As Point3d
    p1.x = ax: p1.y = ay: p1.Z = 0#
    p2.x = bx: p2.y = by: p2.Z = 0#
    Dim oLine As LineElement
    Set oLine = CreateLineElement2(Nothing, p1, p2)
    If color >= 0 Then oLine.color = color
    ' EP CUNG be day net = 0 (khong phu thuoc active weight tren thanh cong cu)
    ' Style de ACTIVE STYLE 0 (DC_MacDinh) lo - vi Element.LineStyle chi-doc, gan = 0 loi bien dich.
    On Error Resume Next
    oLine.LineWeight = 0
    On Error GoTo 0
    ActiveModelReference.AddElement oLine
End Sub

' Ve dau chu thap (tam thua) tai (x,y)
Public Sub VeTam(ByVal x As Double, ByVal y As Double, _
                 ByVal size As Double, Optional ByVal color As Long = -1)
    VeLine x - size, y, x + size, y, color
    VeLine x, y - size, x, y + size, color
End Sub

' SUA 16/10/2026: TAM THUA kieu pho bien (gCadas/famis...): hinh thoi + 4 tia
' net dut, cham tron dac o giua; mau mac dinh 5 (hong). kt = nua duong cheo hinh thoi.
Public Sub VeTamHong(ByVal x As Double, ByVal y As Double, ByVal kt As Double, _
                     Optional ByVal color As Long = 5)
    ' SUA 16/10/2026 (2): gom thanh 1 KHOI (cell "TAMTHUA") nhu phan mem khac
    Dim d As Double, ls As Object, e As Element, o As Object, arr() As Element, n As Long, i As Long
    Dim c As Element
    If kt <= 0 Then kt = 0.3
    If color < 0 Then color = 5
    d = kt
    ReDim arr(0 To 8)
    On Error Resume Next
    Set ls = ActiveDesignFile.LineStyles.Find("2")
    ThemLT arr, n, x, y + d, x + d, y, color, ls
    ThemLT arr, n, x + d, y, x, y - d, color, ls
    ThemLT arr, n, x, y - d, x - d, y, color, ls
    ThemLT arr, n, x - d, y, x, y + d, color, ls
    ThemLT arr, n, x + d, y, x + 2 * d, y, color, ls
    ThemLT arr, n, x - d, y, x - 2 * d, y, color, ls
    ThemLT arr, n, x, y + d, x, y + 2 * d, color, ls
    ThemLT arr, n, x, y - d, x, y - 2 * d, color, ls
    Set e = CreateEllipseElement2(Nothing, Point3dFromXYZ(x, y, 0#), d * 0.3, d * 0.3, Matrix3dIdentity, msdFillModeFilled)
    If Not e Is Nothing Then
        e.color = color
        e.LineWeight = 0
        Set o = e
        o.FillColor = color
        Set arr(n) = e: n = n + 1
    End If
    If n = 0 Then Exit Sub
    ReDim Preserve arr(0 To n - 1)
    Err.Clear
    Set c = CreateCellElement1("TAMTHUA", arr, Point3dFromXYZ(x, y, 0#), False)
    If Err.Number = 0 And Not c Is Nothing Then
        ActiveModelReference.AddElement c
    Else
        For i = 0 To n - 1                       ' du phong: ve roi tung net
            ActiveModelReference.AddElement arr(i)
        Next i
    End If
End Sub

Private Sub ThemLT(arr() As Element, n As Long, ByVal ax As Double, ByVal ay As Double, _
                   ByVal bx As Double, ByVal by As Double, ByVal color As Long, ByVal ls As Object)
    Dim oLine As LineElement
    On Error Resume Next
    Set oLine = CreateLineElement2(Nothing, Point3dFromXYZ(ax, ay, 0#), Point3dFromXYZ(bx, by, 0#))
    If oLine Is Nothing Then Exit Sub
    oLine.color = color
    oLine.LineWeight = 0
    If Not ls Is Nothing Then Set oLine.LineStyle = ls
    Set arr(n) = oLine: n = n + 1
End Sub

' Ve dau X do + o vuong quanh diem ho (giong ve_danh_dau_loi Python, mau 3 = do)
Public Sub VeDanhDauLoi(ByVal x As Double, ByVal y As Double, ByVal size As Double)
    VeLine x - size, y - size, x + size, y + size, 3
    VeLine x - size, y + size, x + size, y - size, 3
    VeLine x - size, y - size, x + size, y - size, 3
    VeLine x + size, y - size, x + size, y + size, 3
    VeLine x + size, y + size, x - size, y + size, 3
    VeLine x - size, y + size, x - size, y - size, 3
End Sub


'============================================================
' TRO GIUP
'============================================================

' Uoc luong kich thuoc dau danh dau tu bounding box du lieu
Private Function KichThuocDau(ByVal minX As Double, ByVal minY As Double, _
                              ByVal maxX As Double, ByVal maxY As Double) As Double
    Dim w As Double, h As Double, s As Double
    w = maxX - minX: h = maxY - minY
    s = (w + h) / 2# / 2000#
    If s <= 0# Then s = 1#
    KichThuocDau = s
End Function

' Lay ten level dang active (de goi y trong hop nhap)
Private Function TenLevelActive() As String
    On Error Resume Next
    TenLevelActive = ActiveSettings.Level.Name
    On Error GoTo 0
End Function


'============================================================
' LENH CHAY DUOC #1: TIM LOI HO RANH
'============================================================
Public Sub DC_TimLoiHoRanh()
    Dim lvName As String, snapStr As String, snap As Double
    lvName = InputBox("Nhap TEN level chua ranh thua." & vbCrLf & _
                      "(De trong = doc tat ca line/linestring)", _
                      "Tim loi ho ranh", TenLevelActive())
    snapStr = InputBox("Dung sai noi diem (snap), don vi ban ve:", _
                       "Tim loi ho ranh", "0.05")
    If snapStr = "" Then Exit Sub
    snap = val(snapStr)
    If snap <= 0 Then snap = 0.05

    Dim minX As Double, minY As Double, maxX As Double, maxY As Double
    Dim segs As Collection
    Set segs = LayCacDoan(snap, lvName, minX, minY, maxX, maxY)
    If segs.Count = 0 Then
        MsgBox "Khong doc duoc doan ranh nao. Kiem tra lai ten level.", _
               vbExclamation, "Tim loi ho ranh"
        Exit Sub
    End If

    Dim ho As Collection
    Set ho = TimDiemHo(segs, snap)

    Dim size As Double
    Dim sizeStr As String
    size = KichThuocDau(minX, minY, maxX, maxY)
    sizeStr = InputBox("Kich thuoc dau X (don vi ban ve):", _
                       "Tim loi ho ranh", Format$(size, "0.###"))
    If sizeStr <> "" Then size = val(sizeStr)
    If size <= 0 Then size = 1

    Dim i As Long, p() As Double
    For i = 1 To ho.Count
        p = ho.Item(i)
        VeDanhDauLoi p(0), p(1), size
    Next i

    MsgBox "So doan ranh doc duoc: " & segs.Count & vbCrLf & _
           "So diem ho ranh (danh dau X do): " & ho.Count, _
           vbInformation, "Tim loi ho ranh"
End Sub


'============================================================
' LENH CHAY DUOC #2: TAO TAM VUNG
'============================================================
Public Sub DC_TaoTamVung()
    Dim lvName As String, snapStr As String, snap As Double
    lvName = InputBox("Nhap TEN level chua ranh thua." & vbCrLf & _
                      "(De trong = doc tat ca line/linestring)", _
                      "Tao tam vung", TenLevelActive())
    snapStr = InputBox("Dung sai noi diem (snap), don vi ban ve:", _
                       "Tao tam vung", "0.05")
    If snapStr = "" Then Exit Sub
    snap = val(snapStr)
    If snap <= 0 Then snap = 0.05

    Dim minX As Double, minY As Double, maxX As Double, maxY As Double
    Dim segs As Collection
    Set segs = LayCacDoan(snap, lvName, minX, minY, maxX, maxY)
    If segs.Count = 0 Then
        MsgBox "Khong doc duoc doan ranh nao.", vbExclamation, "Tao tam vung"
        Exit Sub
    End If

    Dim soTia As Long
    Dim vungs As Collection
    Set vungs = GhepVung(segs, snap, soTia)

    Dim size As Double
    size = KichThuocDau(minX, minY, maxX, maxY)

    Dim i As Long, v As clsVung, tong As Double
    tong = 0#
    For i = 1 To vungs.Count
        Set v = vungs.Item(i)
        VeTam v.cx, v.cy, size, 4   ' mau 4 (thuong la vang) cho de thay
        tong = tong + v.dt
    Next i

    MsgBox "So doan ranh: " & segs.Count & vbCrLf & _
           "So vung (thua) tao duoc: " & vungs.Count & vbCrLf & _
           "So canh cut da tia: " & soTia & vbCrLf & _
           "Tong dien tich: " & Format$(tong, "#,##0.0"), _
           vbInformation, "Tao tam vung"
End Sub

Attribute VB_Name = "modFont"
'============================================================
' modFont - Dat font TrueType co chu Viet cho chu do tool ve
'   May moi cai: font mac dinh cua MicroStation (font so 0/1) KHONG co
'   chu Viet -> chu co dau bi mat. Ham nay dat thang Times New Roman
'   (khong co thi Arial, Tahoma). Goi truoc moi lan ve trich luc.
'   (Module KHONG dung Option Explicit de an toan neu ten hang so
'    msdFontTypeWindowsTrueType khac giua cac ban V8i.)
'============================================================

Public Const DC_FONT_VIET As String = "Times New Roman"

Public Function DC_DatFontViet() As Boolean
    ' Thu lan luot cac font TrueType co san tren moi may Windows
    Dim dS As Variant, i As Long
    dS = Array(DC_FONT_VIET, "Arial", "Tahoma")
    For i = LBound(dS) To UBound(dS)
        If DatMotFont(CStr(dS(i))) Then DC_DatFontViet = True: Exit For
    Next i
    ' doi font co the bat hop "Change Text Attributes" -> tra ve cong cu chon
    On Error Resume Next
    CadInputQueue.SendKeyin "CHOOSE ELEMENT"
End Function

Private Function DatMotFont(ByVal ten As String) As Boolean
    Dim f As Object
    On Error Resume Next
    Set f = ActiveDesignFile.Fonts.Find(msdFontTypeWindowsTrueType, ten)
    If f Is Nothing Then Set f = TimFont(ten)
    If f Is Nothing Then Exit Function
    Err.Clear
    Set ActiveSettings.TextStyle.Font = f       ' font cua chu tool ve (quan trong)
    If Err.Number <> 0 Then
        Err.Clear
        ActiveSettings.TextStyle.Font = f
    End If
    DatMotFont = (Err.Number = 0)
End Function

Private Function TimFont(ByVal ten As String) As Object
    Dim fs As Object, f As Object, i As Long
    On Error Resume Next
    Set fs = ActiveDesignFile.Fonts
    For Each f In fs
        If StrComp(f.Name, ten, vbTextCompare) = 0 Then Set TimFont = f: Exit Function
    Next f
    For i = 0 To 1023
        Set f = Nothing
        Set f = fs.Item(i)
        If Not f Is Nothing Then
            If StrComp(f.Name, ten, vbTextCompare) = 0 Then Set TimFont = f: Exit Function
        End If
    Next i
End Function

Attribute VB_Name = "modGanNhan"
Option Explicit

'============================================================
' modGanNhan - Gan thong tin tu nhan (To, So thua, Loai dat, Ten chu,
'   Dia chi) + ve nhan dia chinh + xuat CSDL ra CSV.
'============================================================

Private Function DocMotText(ByVal el As Element, ByRef x As Double, _
                            ByRef y As Double, ByRef s As String) As Boolean
    DocMotText = False
    s = ""
    Dim o As Point3d
    If el.Type = msdElementTypeText Then
        Dim oT As TextElement
        Set oT = el
        o = oT.Origin: x = o.x: y = o.y
        s = Trim$(oT.Text)
        DocMotText = True
    ElseIf el.Type = msdElementTypeTextNode Then
        Dim oNode As TextNodeElement
        Set oNode = el
        o = oNode.Origin: x = o.x: y = o.y
        Dim subs As ElementEnumerator
        Set subs = oNode.GetSubElements
        Do While subs.MoveNext
            If subs.Current.Type = msdElementTypeText Then
                s = Trim$(subs.Current.AsTextElement.Text)
                If Len(s) > 0 Then Exit Do
            End If
        Loop
        DocMotText = True
    End If
End Function

Private Function LayTruong(ByVal v As clsVung, ByVal t As String) As String
    Select Case t
        Case "so_thua": LayTruong = v.soThua
        Case "so_to": LayTruong = v.SoTo
        Case "loai_dat": LayTruong = v.loaiDat
        Case "ten_chu": LayTruong = v.TenChu
        Case "dia_chi": LayTruong = v.DiaChi
    End Select
End Function

Private Sub DatTruong(ByVal v As clsVung, ByVal t As String, ByVal g As String)
    Select Case t
        Case "so_thua": v.soThua = g
        Case "so_to": v.SoTo = g
        Case "loai_dat": v.loaiDat = g
        Case "ten_chu": v.TenChu = g
        Case "dia_chi": v.DiaChi = g
    End Select
End Sub

' Gan text tren 1 level vao 1 truong cua thua chua no. Tra ve so gan duoc.
Private Function GanTruongMR(ByVal vungs As Collection, ByVal levelName As String, _
                             ByVal truong As String) As Long
    If Len(Trim$(levelName)) = 0 Then Exit Function
    Dim esc As ElementScanCriteria
    Set esc = New ElementScanCriteria
    esc.ExcludeAllTypes
    esc.IncludeType msdElementTypeText
    esc.IncludeType msdElementTypeTextNode
    Dim lv As Level
    On Error Resume Next
    Set lv = ActiveModelReference.Levels(Trim$(levelName))
    On Error GoTo 0
    If lv Is Nothing Then Exit Function
    esc.ExcludeAllLevels
    esc.IncludeLevel lv

    Dim ee As ElementEnumerator
    Set ee = ActiveModelReference.Scan(esc)
    Dim x As Double, y As Double, s As String, v As clsVung, dem As Long
    Do While ee.MoveNext
        If DocMotText(ee.Current, x, y, s) Then
            If Len(s) > 0 Then
                Set v = TimThuaChua(vungs, x, y)
                If Not v Is Nothing Then
                    If Len(LayTruong(v, truong)) = 0 Then
                        DatTruong v, truong, s
                        dem = dem + 1
                    End If
                End If
            End If
        End If
    Loop
    GanTruongMR = dem
End Function


'============================================================
' CHAY GAN NHAN + (tuy chon) XUAT CSDL
'============================================================
Public Sub ChayGanNhan(ByVal lvRanhCSV As String, _
                       ByVal lvTo As String, ByVal lvSo As String, _
                       ByVal lvLoai As String, ByVal lvChu As String, _
                       ByVal lvDiaChi As String, ByVal snap As Double, _
                       ByVal lvNhan As String, ByVal cao As Double, _
                       ByVal xuatCSDL As Boolean, ByVal pathCSDL As String)

    If snap <= 0 Then snap = 0.05
    Dim minX As Double, minY As Double, maxX As Double, maxY As Double
    Dim segs As Collection
    Set segs = LayDoanNhieuLevel(lvRanhCSV, snap, minX, minY, maxX, maxY)
    If segs.Count = 0 Then
        MsgBox "Khong doc duoc ranh.", vbExclamation, "Gan nhan": Exit Sub
    End If
    Dim tia As Long, vungs As Collection
    Set vungs = GhepVung(segs, snap, tia)
    If vungs.Count = 0 Then MsgBox "Khong ghep duoc vung.", vbExclamation: Exit Sub

    Dim nTo As Long, nSo As Long, nLoai As Long, nChu As Long, nDC As Long
    nTo = GanTruongMR(vungs, lvTo, "so_to")
    nSo = GanTruongMR(vungs, lvSo, "so_thua")
    nLoai = GanTruongMR(vungs, lvLoai, "loai_dat")
    nChu = GanTruongMR(vungs, lvChu, "ten_chu")
    nDC = GanTruongMR(vungs, lvDiaChi, "dia_chi")

    ' Ve nhan (so thua / dien tich / loai dat), to mau theo loai dat
    If Len(Trim$(lvNhan)) > 0 Then
        On Error Resume Next
        ActiveSettings.Level = ActiveModelReference.Levels(Trim$(lvNhan))
        On Error GoTo 0
    End If
    If cao <= 0 Then cao = 1
    Dim i As Long, v As clsVung
    For i = 1 To vungs.Count
        Set v = vungs.Item(i)
        VeNhanThuaDayDu v, cao, "mau"
    Next i

    ' Xuat CSDL
    Dim msgCSDL As String
    If xuatCSDL And Len(Trim$(pathCSDL)) > 0 Then
        If GhiCSV(vungs, pathCSDL) Then
            msgCSDL = vbCrLf & "Da xuat CSDL: " & pathCSDL
        Else
            msgCSDL = vbCrLf & "(Khong ghi duoc CSDL: " & pathCSDL & ")"
        End If
    End If

    MsgBox "So thua: " & vungs.Count & vbCrLf & _
           "Gan To ban do: " & nTo & vbCrLf & _
           "Gan So thua: " & nSo & vbCrLf & _
           "Gan Loai dat: " & nLoai & vbCrLf & _
           "Gan Ten chu: " & nChu & vbCrLf & _
           "Gan Dia chi: " & nDC & msgCSDL, _
           vbInformation, "Gan nhan / CSDL"
End Sub

' Ghi CSDL ra CSV (UTF-8, mo bang Excel)
Private Function GhiCSV(ByVal vungs As Collection, ByVal path As String) As Boolean
    GhiCSV = False
    Dim st As Object
    On Error Resume Next
    Set st = CreateObject("ADODB.Stream")
    On Error GoTo 0
    If st Is Nothing Then Exit Function

    st.Type = 2
    st.Charset = "utf-8"
    st.Open

    st.WriteText "STT,To ban do,So thua,Loai dat,Dien tich(m2),Ten chu,Dia chi" & vbCrLf
    Dim i As Long, v As clsVung, Dong As String
    For i = 1 To vungs.Count
        Set v = vungs.Item(i)
        Dong = i & "," & _
               CsvO(v.SoTo) & "," & CsvO(v.soThua) & "," & CsvO(v.loaiDat) & "," & _
               Format$(Round(v.dt, 1), "0.0") & "," & _
               CsvO(v.TenChu) & "," & CsvO(v.DiaChi)
        st.WriteText Dong & vbCrLf
    Next i

    On Error Resume Next
    st.SaveToFile path, 2      ' 2 = ghi de
    If Err.Number = 0 Then GhiCSV = True
    st.Close
    On Error GoTo 0
End Function

' Boc 1 o CSV (them nhay neu co dau phay/nhay)
Private Function CsvO(ByVal s As String) As String
    If InStr(s, ",") > 0 Or InStr(s, """") > 0 Or InStr(s, vbLf) > 0 Then
        CsvO = """" & Replace(s, """", """""") & """"
    Else
        CsvO = s
    End If
End Function

Attribute VB_Name = "modGanTag"
'============================================================
' modGanTag - Gan chu danh dau (tag) vao bang toa do cua FILE MAU
'   Dung khi lam / sua file mau trich luc: mo file mau .dgn, chon cac
'   duong ke cua bang (ca tieu de cung duoc), chay lenh -> tu do luoi o,
'   dat tag vao giua tung o:
'     bang phu  : tths | tamxhs | tamyhs | cdhs  (cd dat giua 2 hang)
'     bang chinh: tttl | tamYtl | tamXtl | cdtl
'   Tag cung level voi duong ke, chu Times New Roman.
'============================================================
Option Explicit

Private Function tieuDe() As String
    tieuDe = "G" & ChrW(7855) & "n tag b" & ChrW(7843) & "ng t" & ChrW(7885) & "a " & ChrW(273) & ChrW(7897)
End Function

Public Sub DC_GanTagBang()
    Dim ee As ElementEnumerator, el As Element, pts() As Point3d, i As Long, j As Long
    Dim vx As New Collection, hy As New Collection, lv As Level, t As Long
    Dim x1 As Double, x2 As Double, y1 As Double, y2 As Double, dau As Boolean
    On Error Resume Next
    Set ee = ActiveModelReference.GetSelectedElements
    On Error GoTo 0
    If ee Is Nothing Then GoTo ChuaChon
    Do While ee.MoveNext
        Set el = ee.Current
        t = el.Type
        If t = msdElementTypeLine Or t = msdElementTypeLineString Or t = msdElementTypeShape Then
            If lv Is Nothing Then Set lv = el.Level
            If t = msdElementTypeShape Then pts = el.AsShapeElement.GetVertices Else pts = el.AsLineElement.GetVertices
            For i = LBound(pts) To UBound(pts) - 1
                If Abs(pts(i + 1).x - pts(i).x) < 0.001 * Abs(pts(i + 1).y - pts(i).y) Then vx.Add (pts(i).x + pts(i + 1).x) / 2
                If Abs(pts(i + 1).y - pts(i).y) < 0.001 * Abs(pts(i + 1).x - pts(i).x) Then hy.Add (pts(i).y + pts(i + 1).y) / 2
            Next i
            For i = LBound(pts) To UBound(pts)
                If Not dau Then
                    x1 = pts(i).x: x2 = x1: y1 = pts(i).y: y2 = y1: dau = True
                Else
                    If pts(i).x < x1 Then x1 = pts(i).x
                    If pts(i).x > x2 Then x2 = pts(i).x
                    If pts(i).y < y1 Then y1 = pts(i).y
                    If pts(i).y > y2 Then y2 = pts(i).y
                End If
            Next i
        End If
    Loop
    If vx.Count < 2 Or hy.Count < 3 Then GoTo ChuaChon

    Dim tol As Double, xs() As Double, ys() As Double, nX As Long, ny As Long
    tol = (x2 - x1 + y2 - y1) * 0.002
    nX = Gop(vx, tol, xs, False)
    ny = Gop(hy, tol, ys, True)            ' tren xuong
    If nX < 2 Or ny < 3 Then GoTo ChuaChon

    ' Hang tieu de: cac hang dau cao khac hang pho bien
    Dim hTB As Double, nTD As Long, s As String, ok As Boolean
    hTB = CaoPhoBien(ys, ny)
    nTD = 0
    For i = 0 To ny - 2
        If Abs((ys(i) - ys(i + 1)) - hTB) > hTB * 0.15 Then nTD = i + 1 Else Exit For
    Next i
    s = InputBox("Bang co " & (nX - 1) & " cot, " & (ny - 1) & " hang." & vbCrLf & _
                 "So hang TIEU DE tren cung (bo qua, khong dat tag):", "DiaChinhVL", CStr(nTD))
    If StrPtr(s) = 0 Then Exit Sub
    nTD = CLng(val(s))
    If nTD < 0 Or nTD >= ny - 1 Then nTD = 0

    Dim macDinh As String
    Select Case nX - 1
        Case 4: macDinh = "tths,tamxhs,tamyhs,cdhs"
        Case 3: macDinh = "tths,tamxhs,tamyhs"
        Case 2: macDinh = "tths,cdhs"
        Case Else: macDinh = ""
    End Select
    s = InputBox("Tag cho tung cot (trai -> phai, cach nhau dau phay, '-' = bo cot):" & vbCrLf & _
                 "Bang phu: tths,tamxhs,tamyhs,cdhs (X = Bac, Y = Dong)" & vbCrLf & _
                 "Bang chinh: tttl,tamYtl,tamXtl,cdtl", "DiaChinhVL", macDinh)
    If StrPtr(s) = 0 Then Exit Sub
    Dim tg() As String
    tg = Split(Replace(s, " ", ""), ",")
    If UBound(tg) <> nX - 2 Then
        DC_ThongBao "S" & ChrW(7889) & " tag (" & (UBound(tg) + 1) & ") kh" & ChrW(244) & "ng b" & ChrW(7857) & "ng s" & ChrW(7889) & " c" & ChrW(7897) & "t (" & (nX - 1) & ").", tieuDe, vbExclamation
        Exit Sub
    End If

    Dim r As Long, c As Long, xc As Double, yc As Double, cao As Double, dem As Long, cuoi As Long
    cuoi = ny - 2                          ' hang du lieu cuoi (chi so hang)
    For r = nTD To cuoi
        cao = (ys(r) - ys(r + 1)) * 0.45
        For c = 0 To nX - 2
            If Len(tg(c)) > 0 And tg(c) <> "-" Then
                xc = (xs(c) + xs(c + 1)) / 2
                If LCase$(Left$(tg(c), 2)) = "cd" Then
                    If r < cuoi Then
                        yc = ys(r + 1)                 ' canh r -> r+1: giua 2 hang
                        DatTag xc, yc, tg(c), cao, lv: dem = dem + 1
                    End If
                Else
                    yc = (ys(r) + ys(r + 1)) / 2
                    DatTag xc, yc, tg(c), cao, lv: dem = dem + 1
                End If
            End If
        Next c
    Next r
    RedrawAllViews
    DC_ThongBao ChrW(272) & ChrW(227) & " " & ChrW(273) & ChrW(7863) & "t " & dem & " tag v" & ChrW(224) & "o " & (cuoi - nTD + 1) & " h" & ChrW(224) & "ng." & vbCrLf & _
                "L" & ChrW(432) & "u file m" & ChrW(7851) & "u (File > Save) r" & ChrW(7891) & "i xu" & ChrW(7845) & "t tr" & ChrW(237) & "ch l" & ChrW(7909) & "c " & ChrW(273) & ChrW(7875) & " ki" & ChrW(7875) & "m tra." & vbCrLf & _
                "(N" & ChrW(7871) & "u " & ChrW(273) & ChrW(7863) & "t sai: Undo ho" & ChrW(7863) & "c x" & ChrW(243) & "a c" & ChrW(225) & "c ch" & ChrW(7919) & " tag v" & ChrW(7915) & "a " & ChrW(273) & ChrW(7863) & "t.)", tieuDe
    Exit Sub
ChuaChon:
    DC_ThongBao "M" & ChrW(7903) & " file m" & ChrW(7851) & "u, ch" & ChrW(7885) & "n c" & ChrW(225) & "c " & ChrW(273) & ChrW(432) & ChrW(7901) & "ng k" & ChrW(7867) & " c" & ChrW(7911) & "a b" & ChrW(7843) & "ng t" & ChrW(7885) & "a " & ChrW(273) & ChrW(7897) & " (d" & ChrW(249) & "ng Fence ho" & ChrW(7863) & "c k" & ChrW(233) & "o ch" & ChrW(7885) & "n), r" & ChrW(7891) & "i ch" & ChrW(7841) & "y l" & ChrW(7841) & "i l" & ChrW(7879) & "nh.", tieuDe, vbExclamation
End Sub

' Gop cac gia tri gan nhau (< tol) -> mang da sap (giam dan neu giam = True)
Private Function Gop(ByVal dS As Collection, ByVal tol As Double, ByRef kq() As Double, ByVal giam As Boolean) As Long
    Dim a() As Double, n As Long, i As Long, j As Long, t As Double, m As Long
    n = dS.Count
    ReDim a(0 To n - 1)
    For i = 1 To n
        a(i - 1) = dS.Item(i)
    Next i
    For i = 0 To n - 2
        For j = i + 1 To n - 1
            If (a(j) < a(i)) Xor giam Then t = a(i): a(i) = a(j): a(j) = t
        Next j
    Next i
    ReDim kq(0 To n - 1)
    m = 0
    For i = 0 To n - 1
        If m = 0 Then
            kq(0) = a(i): m = 1
        ElseIf Abs(a(i) - kq(m - 1)) > tol Then
            kq(m) = a(i): m = m + 1
        End If
    Next i
    ReDim Preserve kq(0 To m - 1)
    Gop = m
End Function

' Chieu cao hang xuat hien nhieu nhat
Private Function CaoPhoBien(ByRef ys() As Double, ByVal n As Long) As Double
    Dim i As Long, j As Long, dem As Long, demMax As Long, h As Double, hj As Double
    For i = 0 To n - 2
        h = ys(i) - ys(i + 1): dem = 0
        For j = 0 To n - 2
            hj = ys(j) - ys(j + 1)
            If Abs(hj - h) <= h * 0.05 Then dem = dem + 1
        Next j
        If dem > demMax Then demMax = dem: CaoPhoBien = h
    Next i
End Function

Private Sub DatTag(ByVal x As Double, ByVal y As Double, ByVal s As String, ByVal cao As Double, ByVal lv As Level)
    Dim t As TextElement, ts As TextStyle, f As Object
    On Error Resume Next
    Set t = CreateTextElement1(Nothing, s, Point3dFromXYZ(x, y, 0#), Matrix3dIdentity)
    If t Is Nothing Then Exit Sub
    Set ts = t.TextStyle
    ts.Height = cao: ts.Width = cao
    ts.Justification = msdTextJustificationCenterCenter
    For Each f In ActiveDesignFile.Fonts
        If StrComp(f.Name, DC_FONT_VIET, vbTextCompare) = 0 Then Set ts.Font = f: Exit For
    Next f
    Set t.TextStyle = ts
    If Err.Number <> 0 Then Err.Clear: t.TextStyle = ts
    If Not lv Is Nothing Then Set t.Level = lv
    t.LineWeight = 0
    ActiveModelReference.AddElement t
End Sub

Attribute VB_Name = "modHinhHoc"
Option Explicit
' SUA 05/11: dien tich vung nho nhat GhepVung giu lai (0 = mac dinh 1 m2). modKiemVung dat nho de bat vung manh.
Public gGhepVungMin As Double

'============================================================
' modHinhHoc - Hinh hoc & to-po (khong phu thuoc MicroStation)
' Port tu DiaChinhVL_GUI.py:
'   diem_trong_polygon, kc_diem_doan, kc_toi_ranh,
'   centroid_hinh_hoc, tam_can_giua,
'   xay_graph, tim_diem_ho, ghep_vung
'
' QUY UOC DU LIEU (dung chung ca du an):
'   Diem  : mang Double(0 To 1) -> (x, y)
'   Seg   : mang Double(0 To 3) -> (x1, y1, x2, y2)
'   Segs  : Collection cac Seg
'   Ring  : mang Double(0 To n, 0 To 1), vong KIN (Ring(n)=Ring(0)),
'           n = UBound(Ring,1) = so dinh phan biet
'============================================================


'--- Tao mot Seg tu 2 diem ---
Public Function NewSeg(ByVal ax As Double, ByVal ay As Double, _
                       ByVal bx As Double, ByVal by As Double) As Double()
    Dim s(0 To 3) As Double
    s(0) = ax: s(1) = ay: s(2) = bx: s(3) = by
    NewSeg = s
End Function

'--- Tao mot Diem ---
Public Function NewPt(ByVal x As Double, ByVal y As Double) As Double()
    Dim p(0 To 1) As Double
    p(0) = x: p(1) = y
    NewPt = p
End Function


'============================================================
' atan2 (VBA khong co san)
'============================================================
Public Function Atan2(ByVal y As Double, ByVal x As Double) As Double
    Const PI As Double = 3.14159265358979
    If x > 0 Then
        Atan2 = Atn(y / x)
    ElseIf x < 0 Then
        If y >= 0 Then
            Atan2 = Atn(y / x) + PI
        Else
            Atan2 = Atn(y / x) - PI
        End If
    Else ' x = 0
        If y > 0 Then
            Atan2 = PI / 2
        ElseIf y < 0 Then
            Atan2 = -PI / 2
        Else
            Atan2 = 0#
        End If
    End If
End Function

Private Function Hypot(ByVal dx As Double, ByVal dy As Double) As Double
    Hypot = Sqr(dx * dx + dy * dy)
End Function


'============================================================
' diem_trong_polygon
' ring KIN, n = UBound(ring,1)
'============================================================
Public Function DiemTrongPolygon(ByRef ring() As Double, _
                                 ByVal x As Double, ByVal y As Double) As Boolean
    Dim n As Long, i As Long, j As Long
    Dim xi As Double, yi As Double, xj As Double, yj As Double
    Dim trong As Boolean
    n = UBound(ring, 1)          ' so dinh phan biet
    If n < 3 Then
        DiemTrongPolygon = False
        Exit Function
    End If
    trong = False
    j = n - 1
    For i = 0 To n - 1
        xi = ring(i, 0): yi = ring(i, 1)
        xj = ring(j, 0): yj = ring(j, 1)
        If ((yi > y) <> (yj > y)) Then
            If (x < (xj - xi) * (y - yi) / (yj - yi + 1E-30) + xi) Then
                trong = Not trong
            End If
        End If
        j = i
    Next i
    DiemTrongPolygon = trong
End Function


'============================================================
' kc_diem_doan - khoang cach tu diem p toi doan a-b
'============================================================
Public Function KcDiemDoan(ByVal px As Double, ByVal py As Double, _
                           ByVal ax As Double, ByVal ay As Double, _
                           ByVal bx As Double, ByVal by As Double) As Double
    Dim dx As Double, dy As Double, L2 As Double, t As Double
    dx = bx - ax: dy = by - ay
    L2 = dx * dx + dy * dy
    If L2 = 0# Then
        KcDiemDoan = Hypot(px - ax, py - ay)
        Exit Function
    End If
    t = ((px - ax) * dx + (py - ay) * dy) / L2
    If t < 0# Then t = 0#
    If t > 1# Then t = 1#
    KcDiemDoan = Hypot(px - (ax + t * dx), py - (ay + t * dy))
End Function


'============================================================
' kc_toi_ranh - khoang cach nho nhat tu diem toi bien ring
'============================================================
Public Function KcToiRanh(ByRef ring() As Double, _
                          ByVal px As Double, ByVal py As Double) As Double
    Dim n As Long, i As Long, d As Double, best As Double
    n = UBound(ring, 1)
    best = 1E+30
    For i = 0 To n - 1
        d = KcDiemDoan(px, py, ring(i, 0), ring(i, 1), ring(i + 1, 0), ring(i + 1, 1))
        If d < best Then best = d
    Next i
    KcToiRanh = best
End Function


'============================================================
' centroid_hinh_hoc -> tra ve qua ByRef cx, cy
'============================================================
Public Sub CentroidHinhHoc(ByRef ring() As Double, _
                           ByRef cx As Double, ByRef cy As Double)
    Dim n As Long, i As Long, j As Long
    Dim a As Double, sx As Double, sy As Double, cr As Double
    Dim xmin As Double, xmax As Double, ymin As Double, ymax As Double
    n = UBound(ring, 1)
    a = 0#: sx = 0#: sy = 0#
    For i = 0 To n - 1
        j = (i + 1) Mod n
        cr = ring(i, 0) * ring(j, 1) - ring(j, 0) * ring(i, 1)
        a = a + cr
        sx = sx + (ring(i, 0) + ring(j, 0)) * cr
        sy = sy + (ring(i, 1) + ring(j, 1)) * cr
    Next i
    a = a / 2#
    If Abs(a) < 0.000000001 Then
        xmin = ring(0, 0): xmax = ring(0, 0)
        ymin = ring(0, 1): ymax = ring(0, 1)
        For i = 1 To n - 1
            If ring(i, 0) < xmin Then xmin = ring(i, 0)
            If ring(i, 0) > xmax Then xmax = ring(i, 0)
            If ring(i, 1) < ymin Then ymin = ring(i, 1)
            If ring(i, 1) > ymax Then ymax = ring(i, 1)
        Next i
        cx = (xmin + xmax) / 2#
        cy = (ymin + ymax) / 2#
        Exit Sub
    End If
    cx = sx / (6# * a)
    cy = sy / (6# * a)
End Sub


'============================================================
' tam_can_giua -> tra ve tam dat nhan qua ByRef cx, cy
' daoColl: Collection cac ring dao (co the rong)
'============================================================
Public Sub TamCanGiua(ByRef ring() As Double, ByVal daoColl As Collection, _
                      ByRef cx As Double, ByRef cy As Double)
    Dim n As Long, i As Long
    Dim X0 As Double, x1 As Double, Y0 As Double, y1 As Double
    Dim gcx As Double, gcy As Double
    Dim bestX As Double, bestY As Double, bestD As Double, bestGc As Double
    Dim N14 As Long, gx As Long, gy As Long
    Dim px As Double, py As Double, d As Double, dgc As Double
    Dim step As Double, ddx As Long, ddy As Long, k As Long
    Dim co As Boolean

    n = UBound(ring, 1)
    X0 = ring(0, 0): x1 = ring(0, 0): Y0 = ring(0, 1): y1 = ring(0, 1)
    For i = 1 To n - 1
        If ring(i, 0) < X0 Then X0 = ring(i, 0)
        If ring(i, 0) > x1 Then x1 = ring(i, 0)
        If ring(i, 1) < Y0 Then Y0 = ring(i, 1)
        If ring(i, 1) > y1 Then y1 = ring(i, 1)
    Next i

    CentroidHinhHoc ring, gcx, gcy

    ' Uu tien trong tam neu no hop le
    If TCG_HopLe(ring, daoColl, gcx, gcy) Then
        cx = gcx: cy = gcy
        Exit Sub
    End If

    ' Pole of inaccessibility (luoi tho -> tinh dan)
    bestD = -1#: bestGc = 1E+30
    co = False
    N14 = 14
    For gx = 0 To N14
        For gy = 0 To N14
            px = X0 + (x1 - X0) * gx / N14
            py = Y0 + (y1 - Y0) * gy / N14
            If TCG_HopLe(ring, daoColl, px, py) Then
                d = TCG_Kc(ring, daoColl, px, py)
                dgc = Hypot(px - gcx, py - gcy)
                If (d > bestD * 1.01) Or (d > bestD * 0.99 And dgc < bestGc) Then
                    If d > bestD Then bestD = d
                    bestX = px: bestY = py: bestGc = dgc
                    co = True
                End If
            End If
        Next gy
    Next gx

    If Not co Then
        ' SUA 07/11: vung dai/hep (duong, kenh) luoi 15x15 khong roi vao trong -> truoc day lay
        '   trong tam (nam NGOAI vung, roi vao thua ben canh -> 2 tam 1 thua). Nay quet ngang tim diem trong.
        If TCG_QuetNgang(ring, daoColl, X0, x1, Y0, y1, gcx, gcy, bestX, bestY) Then
            cx = bestX: cy = bestY
        Else
            cx = gcx: cy = gcy
        End If
        Exit Sub
    End If

    step = x1 - X0
    If (y1 - Y0) > step Then step = (y1 - Y0)
    step = step / N14
    For k = 1 To 2
        step = step / 4#
        For ddx = -2 To 2
            For ddy = -2 To 2
                px = bestX + ddx * step
                py = bestY + ddy * step
                If TCG_HopLe(ring, daoColl, px, py) Then
                    d = TCG_Kc(ring, daoColl, px, py)
                    dgc = Hypot(px - gcx, py - gcy)
                    If (d > bestD * 1.01) Or (d > bestD * 0.99 And dgc < bestGc) Then
                        If d > bestD Then bestD = d
                        bestX = px: bestY = py: bestGc = dgc
                    End If
                End If
            Next ddy
        Next ddx
    Next k

    cx = bestX: cy = bestY
End Sub

' SUA 07/11: tim diem TRONG vung bang cac duong quet ngang + doc (cho vung dai, hep)
'   Chon doan trong dai nhat; uu tien gan trong tam khi xap xi bang nhau.
Private Function TCG_QuetNgang(ByRef ring() As Double, ByVal daoColl As Collection, _
                               ByVal X0 As Double, ByVal x1 As Double, ByVal Y0 As Double, ByVal y1 As Double, _
                               ByVal gcx As Double, ByVal gcy As Double, _
                               ByRef bx As Double, ByRef by As Double) As Boolean
    Const NQ As Long = 80
    Dim n As Long, i As Long, k As Long, h As Long, m As Long, j As Long
    Dim c As Double, xs() As Double, t As Double, L As Double, mx As Double, bestL As Double, dgc As Double, bestG As Double
    Dim ai As Double, aj As Double, bi As Double, bj As Double
    n = UBound(ring, 1)
    If n < 3 Then Exit Function
    ReDim xs(0 To n + 1)
    bestL = -1#: bestG = 1E+30
    For h = 0 To 1                       ' 0: quet ngang (y co dinh), 1: quet doc (x co dinh)
        For k = 1 To NQ
            If h = 0 Then c = Y0 + (y1 - Y0) * (k - 0.5) / NQ Else c = X0 + (x1 - X0) * (k - 0.5) / NQ
            m = 0
            For i = 0 To n - 1
                If h = 0 Then
                    ai = ring(i, 1): aj = ring(i + 1, 1): bi = ring(i, 0): bj = ring(i + 1, 0)
                Else
                    ai = ring(i, 0): aj = ring(i + 1, 0): bi = ring(i, 1): bj = ring(i + 1, 1)
                End If
                If (ai > c) <> (aj > c) Then
                    xs(m) = bi + (c - ai) * (bj - bi) / (aj - ai)
                    m = m + 1
                End If
            Next i
            ' sap xep
            For i = 0 To m - 2
                For j = i + 1 To m - 1
                    If xs(j) < xs(i) Then t = xs(i): xs(i) = xs(j): xs(j) = t
                Next j
            Next i
            For i = 0 To m - 2 Step 2
                L = xs(i + 1) - xs(i)
                mx = (xs(i) + xs(i + 1)) / 2#
                If L > bestL * 0.98 Then
                    If h = 0 Then dgc = Hypot(mx - gcx, c - gcy) Else dgc = Hypot(c - gcx, mx - gcy)
                    If (L > bestL * 1.02) Or (dgc < bestG) Then
                        If h = 0 Then
                            If TCG_HopLe(ring, daoColl, mx, c) Then bestL = IIf(L > bestL, L, bestL): bestG = dgc: bx = mx: by = c: TCG_QuetNgang = True
                        Else
                            If TCG_HopLe(ring, daoColl, c, mx) Then bestL = IIf(L > bestL, L, bestL): bestG = dgc: bx = c: by = mx: TCG_QuetNgang = True
                        End If
                    End If
                End If
            Next i
        Next k
    Next h
End Function

Private Function TCG_HopLe(ByRef ring() As Double, ByVal daoColl As Collection, _
                           ByVal px As Double, ByVal py As Double) As Boolean
    Dim k As Long, dr() As Double
    If Not DiemTrongPolygon(ring, px, py) Then
        TCG_HopLe = False
        Exit Function
    End If
    If Not daoColl Is Nothing Then
        For k = 1 To daoColl.Count
            dr = daoColl.Item(k)
            If DiemTrongPolygon(dr, px, py) Then
                TCG_HopLe = False
                Exit Function
            End If
        Next k
    End If
    TCG_HopLe = True
End Function

Private Function TCG_Kc(ByRef ring() As Double, ByVal daoColl As Collection, _
                        ByVal px As Double, ByVal py As Double) As Double
    Dim d As Double, d2 As Double, k As Long, dr() As Double
    d = KcToiRanh(ring, px, py)
    If Not daoColl Is Nothing Then
        For k = 1 To daoColl.Count
            dr = daoColl.Item(k)
            d2 = KcToiRanh(dr, px, py)
            If d2 < d Then d = d2
        Next k
    End If
    TCG_Kc = d
End Function


'============================================================
' XAY GRAPH (dung chung cho tim_diem_ho va ghep_vung)
' Ket qua tra ve qua ByRef:
'   nodeX(), nodeY()  : toa do node (0..nodeCount-1)
'   eu(), ev()        : cap node cua canh (0..edgeCount-1)
'============================================================
Private Sub XayGraph(ByVal segs As Collection, ByVal snap As Double, _
                     ByRef nodeX() As Double, ByRef nodeY() As Double, _
                     ByRef nodeCount As Long, _
                     ByRef eU() As Long, ByRef ev() As Long, _
                     ByRef edgeCount As Long)
    Dim nodeMap As Object, edgeSet As Object
    Dim s() As Double, i As Long
    Dim u As Long, v As Long
    Dim ekey As String
    Dim capX As Long, capE As Long

    Set nodeMap = CreateObject("Scripting.Dictionary")
    Set edgeSet = CreateObject("Scripting.Dictionary")

    capX = 256: capE = 256
    ReDim nodeX(0 To capX - 1)
    ReDim nodeY(0 To capX - 1)
    ReDim eU(0 To capE - 1)
    ReDim ev(0 To capE - 1)
    nodeCount = 0
    edgeCount = 0

    If segs Is Nothing Then Exit Sub

    For i = 1 To segs.Count
        s = segs.Item(i)
        u = FindNode(s(0), s(1), snap, nodeMap, nodeX, nodeY, nodeCount, capX)
        v = FindNode(s(2), s(3), snap, nodeMap, nodeX, nodeY, nodeCount, capX)
        If u <> v Then
            If u < v Then
                ekey = u & "|" & v
            Else
                ekey = v & "|" & u
            End If
            If Not edgeSet.Exists(ekey) Then
                edgeSet.Add ekey, True
                If edgeCount >= capE Then
                    capE = capE * 2
                    ReDim Preserve eU(0 To capE - 1)
                    ReDim Preserve ev(0 To capE - 1)
                End If
                eU(edgeCount) = u
                ev(edgeCount) = v
                edgeCount = edgeCount + 1
            End If
        End If
    Next i
End Sub

Private Function FindNode(ByVal x As Double, ByVal y As Double, ByVal snap As Double, _
                          ByVal nodeMap As Object, _
                          ByRef nodeX() As Double, ByRef nodeY() As Double, _
                          ByRef nodeCount As Long, ByRef capX As Long) As Long
    Dim key As String, idx As Long
    ' SUA 08/11: CLng tran so (loi 6 Overflow) khi toa do / snap > 2,1 ty (doi tuong o rat xa, snap nho)
    key = Format$(RoundHalf(x / snap), "0") & "|" & Format$(RoundHalf(y / snap), "0")
    If nodeMap.Exists(key) Then
        FindNode = nodeMap.Item(key)
        Exit Function
    End If
    If nodeCount >= capX Then
        capX = capX * 2
        ReDim Preserve nodeX(0 To capX - 1)
        ReDim Preserve nodeY(0 To capX - 1)
    End If
    idx = nodeCount
    nodeX(idx) = x
    nodeY(idx) = y
    nodeMap.Add key, idx
    nodeCount = nodeCount + 1
    FindNode = idx
End Function

' Lam tron ".5 ra so chan" giong Python round() (banker's rounding)
Private Function RoundHalf(ByVal v As Double) As Double
    RoundHalf = Round(v, 0)
End Function


'============================================================
' tim_diem_ho -> Collection cac Diem (mang Double(0..1)) bac 1
'============================================================
Public Function TimDiemHo(ByVal segs As Collection, ByVal snap As Double) As Collection
    Dim nodeX() As Double, nodeY() As Double, nodeCount As Long
    Dim eU() As Long, ev() As Long, edgeCount As Long
    Dim deg() As Long, i As Long
    Dim ket As New Collection

    XayGraph segs, snap, nodeX, nodeY, nodeCount, eU, ev, edgeCount
    If nodeCount = 0 Then
        Set TimDiemHo = ket
        Exit Function
    End If
    ReDim deg(0 To nodeCount - 1)
    For i = 0 To edgeCount - 1
        deg(eU(i)) = deg(eU(i)) + 1
        deg(ev(i)) = deg(ev(i)) + 1
    Next i
    For i = 0 To nodeCount - 1
        If deg(i) = 1 Then
            ket.Add NewPt(nodeX(i), nodeY(i))
        End If
    Next i
    Set TimDiemHo = ket
End Function


'============================================================
' ghep_vung -> Collection cac clsVung ; soTia tra ve ByRef
'============================================================
' TU VA HO RANH: noi 2 dau ranh ho (bac 1) nam gan nhau trong gapTol.
' Chi noi cap dau ho gan nhau nhat, khoang cach > snap va <= gapTol.
' Tra ve segs da them cac doan noi. gapTol <= 0 -> giu nguyen.
Public Function VaHoRanh(ByVal segs As Collection, ByVal snap As Double, _
                         ByVal gapTol As Double) As Collection
    Dim res As New Collection, i As Long, j As Long
    For i = 1 To segs.Count
        res.Add segs.Item(i)
    Next i
    If gapTol <= 0 Then Set VaHoRanh = res: Exit Function

    Dim ho As Collection
    Set ho = TimDiemHo(segs, snap)
    Dim n As Long: n = ho.Count
    If n < 2 Then Set VaHoRanh = res: Exit Function

    Dim used() As Boolean: ReDim used(1 To n)
    Dim a() As Double, b() As Double, d As Double, best As Long, bestD As Double
    For i = 1 To n
        If Not used(i) Then
            a = ho.Item(i)
            best = -1: bestD = gapTol + 0.000001
            For j = 1 To n
                If j <> i And Not used(j) Then
                    b = ho.Item(j)
                    d = Sqr((b(0) - a(0)) ^ 2 + (b(1) - a(1)) ^ 2)
                    If d > snap And d <= gapTol And d < bestD Then bestD = d: best = j
                End If
            Next j
            If best > 0 Then
                b = ho.Item(best)
                res.Add NewSeg(a(0), a(1), b(0), b(1))
                used(i) = True: used(best) = True
            End If
        End If
    Next i
    Set VaHoRanh = res
End Function

Public Function GhepVung(ByVal segs As Collection, ByVal snap As Double, _
                         ByRef soTia As Long) As Collection
    Dim nodeX() As Double, nodeY() As Double, nodeCount As Long
    Dim eU() As Long, ev() As Long, edgeCount As Long
    Dim deg() As Long, alive() As Boolean
    Dim i As Long, j As Long, u As Long, v As Long, w As Long
    Dim thayDoi As Boolean
    Dim parent() As Long

    Dim ket As New Collection
    soTia = 0

    ' SUA 11/10/2026: cat cac doan tai giao diem (net ve cat ngang nhau / dau mut
    ' cham giua doan khac, vd SmartLine ve du qua goc) -> moi giao diem thanh nut.
    Set segs = NoiDoanGiao(segs, snap)
    XayGraph segs, snap, nodeX, nodeY, nodeCount, eU, ev, edgeCount
    If edgeCount = 0 Then
        Set GhepVung = ket
        Exit Function
    End If

    '--- Bac cac node ---
    ReDim deg(0 To nodeCount - 1)
    For i = 0 To edgeCount - 1
        deg(eU(i)) = deg(eU(i)) + 1
        deg(ev(i)) = deg(ev(i)) + 1
    Next i

    '--- Tia cac canh cut (bac 1) lap lai ---
    ReDim alive(0 To edgeCount - 1)
    For i = 0 To edgeCount - 1
        alive(i) = True
    Next i
    thayDoi = True
    Do While thayDoi
        thayDoi = False
        For i = 0 To edgeCount - 1
            If alive(i) Then
                u = eU(i): v = ev(i)
                If deg(u) <= 1 Or deg(v) <= 1 Then
                    alive(i) = False
                    deg(u) = deg(u) - 1
                    deg(v) = deg(v) - 1
                    soTia = soTia + 1
                    thayDoi = True
                End If
            End If
        Next i
    Loop

    '--- Union-Find tren cac canh con song ---
    ReDim parent(0 To nodeCount - 1)
    For i = 0 To nodeCount - 1
        parent(i) = i
    Next i
    For i = 0 To edgeCount - 1
        If alive(i) Then UF_Union parent, eU(i), ev(i)
    Next i

    '--- Ke (adjacency) + sap xep theo goc + pos ---
    Dim adjD As Object, posD As Object
    Set adjD = CreateObject("Scripting.Dictionary")   ' node -> Long() neighbor da sap xep
    Set posD = CreateObject("Scripting.Dictionary")   ' "a|w" -> chi so trong danh sach ke cua a

    ' Dem so ke moi node
    Dim cnt() As Long
    ReDim cnt(0 To nodeCount - 1)
    For i = 0 To edgeCount - 1
        If alive(i) Then
            cnt(eU(i)) = cnt(eU(i)) + 1
            cnt(ev(i)) = cnt(ev(i)) + 1
        End If
    Next i

    ' Dua ke vao mang tam
    Dim tmpN As Object
    Set tmpN = CreateObject("Scripting.Dictionary")   ' node -> Collection ke
    For i = 0 To edgeCount - 1
        If alive(i) Then
            AddNeighbor tmpN, eU(i), ev(i)
            AddNeighbor tmpN, ev(i), eU(i)
        End If
    Next i

    Dim keyA As Variant, a As Long
    Dim lst As Collection, arrN() As Long, ang() As Double, m As Long
    For Each keyA In tmpN.Keys
        a = CLng(keyA)
        Set lst = tmpN.Item(keyA)
        m = lst.Count
        ReDim arrN(0 To m - 1)
        ReDim ang(0 To m - 1)
        For j = 0 To m - 1
            arrN(j) = lst.Item(j + 1)
            ang(j) = Atan2(nodeY(arrN(j)) - nodeY(a), nodeX(arrN(j)) - nodeX(a))
        Next j
        SortByAngle arrN, ang
        adjD.Add a, arrN
        For j = 0 To m - 1
            posD.Add a & "|" & arrN(j), j
        Next j
    Next keyA

    '--- Truy vet mat (faces) ---
    Dim unused As Object
    Set unused = CreateObject("Scripting.Dictionary")
    For i = 0 To edgeCount - 1
        If alive(i) Then
            unused.Add eU(i) & "|" & ev(i), True
            unused.Add ev(i) & "|" & eU(i), True
        End If
    Next i

    ' Cac face duong (dat) va face am (dao)
    Dim faceRings As New Collection   ' moi phan tu: ring() 2 chieu
    Dim faceArea As New Collection    ' Double (dien tich CON LAI sau khi tru dao)
    Dim faceGoc As New Collection     ' Double (dien tich GOC - dung so sanh chua dao)
    Dim faceComp As New Collection    ' Long
    Dim faceDao As New Collection     ' Collection cac ring dao (khoi tao rong)

    Dim daoRings As New Collection
    Dim daoArea As New Collection
    Dim daoComp As New Collection

    Dim startKey As Variant, su As Long, sv As Long
    Dim ringNodes() As Long, rN As Long, capRn As Long
    Dim guard As Long, ii As Long, lstAdj() As Long
    Dim comp As Long
    Dim ring() As Double, nn As Long, kk As Long
    Dim Aria As Double   ' dien tich co dau - PHAI Double (toa do VN2000 lon -> Long bi Overflow)

    Do While unused.Count > 0
        ' lay 1 canh huong bat ky con lai
        startKey = unused.Keys()(0)
        ParseKey CStr(startKey), su, sv
        u = su: v = sv

        capRn = 64
        ReDim ringNodes(0 To capRn - 1)
        rN = 0
        ringNodes(rN) = u: rN = rN + 1

        Dim okFace As Boolean
        okFace = False
        For guard = 0 To edgeCount * 2
            If Not unused.Exists(u & "|" & v) Then Exit For
            unused.Remove u & "|" & v
            If rN >= capRn Then
                capRn = capRn * 2
                ReDim Preserve ringNodes(0 To capRn - 1)
            End If
            ringNodes(rN) = v: rN = rN + 1
            ii = posD.Item(v & "|" & u)
            lstAdj = adjD.Item(v)
            Dim mm As Long
            mm = UBound(lstAdj) + 1
            w = lstAdj(((ii - 1) + mm) Mod mm)   ' (i-1) mod len, tranh am
            u = v: v = w
            If u = su And v = sv Then
                okFace = True
                Exit For
            End If
        Next guard

        If okFace And rN >= 4 Then
            ' dung ring (KIN: ringNodes(0)=ringNodes(rn-1))
            nn = rN - 1                 ' so dinh phan biet
            ReDim ring(0 To nn, 0 To 1)
            For kk = 0 To nn
                ring(kk, 0) = nodeX(ringNodes(kk))
                ring(kk, 1) = nodeY(ringNodes(kk))
            Next kk
            comp = UF_Find(parent, ringNodes(0))
            ' dien tich co dau (Double - tranh Overflow voi toa do lon)
            Aria = 0#
            For kk = 0 To nn - 1
                Aria = Aria + ring(kk, 0) * ring(kk + 1, 1) - ring(kk + 1, 0) * ring(kk, 1)
            Next kk
            Aria = Aria / 2#
            If Abs(Aria) >= IIf(gGhepVungMin > 0#, gGhepVungMin, 1#) Then
                If Aria > 0 Then
                    faceRings.Add ring
                    faceArea.Add Aria
                    faceGoc.Add Aria
                    faceComp.Add comp
                    faceDao.Add New Collection
                Else
                    daoRings.Add ring
                    daoArea.Add Abs(Aria)
                    daoComp.Add comp
                End If
            End If
        End If
    Loop

    '--- Gan dao vao face nho nhat chua no (khac component) & tru dien tich ---
    Dim di As Long, fi As Long, best As Long
    Dim bestArea As Double, hasBest As Boolean
    Dim ringD() As Double, Af As Double, ringF() As Double
    Dim ptx As Double, pty As Double, aMoi As Double

    For di = 1 To daoRings.Count
        ringD = daoRings.Item(di)
        ptx = ringD(0, 0): pty = ringD(0, 1)
        best = -1: hasBest = False: bestArea = 0#
        For fi = 1 To faceRings.Count
            If faceComp.Item(fi) <> daoComp.Item(di) Then
                ' SUA 11/10/2026: so sanh bang dien tich GOC. Truoc day dung dien
                ' tich da tru dao -> thua co nhieu thua con lot trong (vd 843 to 69)
                ' sau khi tru dao nho thi "nho hon" dao lon -> dao lon bi gan sai /
                ' bi bo -> trich luc thieu canh thua con.
                Af = faceGoc.Item(fi)
                If Af > daoArea.Item(di) Then
                    ringF = faceRings.Item(fi)
                    If DiemTrongPolygon(ringF, ptx, pty) Then
                        If (Not hasBest) Or (Af < bestArea) Then
                            best = fi
                            bestArea = Af
                            hasBest = True
                        End If
                    End If
                End If
            End If
        Next fi
        If hasBest Then
            aMoi = faceArea.Item(best) - daoArea.Item(di)
            If aMoi > 1# Then
                ' cap nhat dien tich (Collection khong sua item -> thay bang mang phu)
                Call CollectionSet(faceArea, best, aMoi)
                faceDao.Item(best).Add ringD
            End If
        End If
    Next di

    '--- Tao clsVung ---
    Dim fk As Long, vg As clsVung, cx As Double, cy As Double
    Dim daoColl As Collection, rf() As Double
    For fk = 1 To faceRings.Count
        Set vg = New clsVung
        rf = faceRings.Item(fk)
        vg.ring = rf
        vg.HasRing = True
        Set daoColl = faceDao.Item(fk)
        Set vg.dao = daoColl
        vg.NDao = daoColl.Count
        vg.dt = faceArea.Item(fk)
        TamCanGiua rf, daoColl, cx, cy
        vg.cx = cx
        vg.cy = cy
        ket.Add vg
    Next fk

    Set GhepVung = ket
End Function


'============================================================
' Tro giup
'============================================================
Private Sub AddNeighbor(ByVal tmpN As Object, ByVal a As Long, ByVal b As Long)
    Dim c As Collection
    If tmpN.Exists(a) Then
        Set c = tmpN.Item(a)
    Else
        Set c = New Collection
        tmpN.Add a, c
    End If
    c.Add b
End Sub

Private Sub SortByAngle(ByRef arrN() As Long, ByRef ang() As Double)
    ' Insertion sort tang dan theo goc
    Dim i As Long, j As Long, kn As Long
    Dim ka As Double
    For i = 1 To UBound(arrN)
        kn = arrN(i): ka = ang(i)
        j = i - 1
        Do While j >= 0
            If ang(j) > ka Then
                arrN(j + 1) = arrN(j)
                ang(j + 1) = ang(j)
                j = j - 1
            Else
                Exit Do
            End If
        Loop
        arrN(j + 1) = kn
        ang(j + 1) = ka
    Next i
End Sub

Private Sub ParseKey(ByVal s As String, ByRef a As Long, ByRef b As Long)
    Dim p As Long
    p = InStr(s, "|")
    a = CLng(Left$(s, p - 1))
    b = CLng(Mid$(s, p + 1))
End Sub

'--- Union-Find ---
Private Function UF_Find(ByRef parent() As Long, ByVal x As Long) As Long
    Dim r As Long, nX As Long
    r = x
    Do While parent(r) <> r
        r = parent(r)
    Loop
    ' nen duong
    Do While parent(x) <> x
        nX = parent(x)
        parent(x) = r
        x = nX
    Loop
    UF_Find = r
End Function

Private Sub UF_Union(ByRef parent() As Long, ByVal a As Long, ByVal b As Long)
    Dim ra As Long, rb As Long
    ra = UF_Find(parent, a)
    rb = UF_Find(parent, b)
    If ra <> rb Then parent(ra) = rb
End Sub

' Collection VBA khong sua item tai cho -> ham thay gia tri o vi tri idx
Private Sub CollectionSet(ByRef c As Collection, ByVal idx As Long, ByVal val As Variant)
    Dim i As Long, tmp As New Collection
    For i = 1 To c.Count
        If i = idx Then
            tmp.Add val
        Else
            tmp.Add c.Item(i)
        End If
    Next i
    Set c = tmp
End Sub


'============================================================
' NOI DOAN TAI GIAO DIEM (dung luoi o vuong de nhanh voi ca to ban do)
'   - Hai doan cat nhau / dau mut nam tren doan kia (sai so tol) -> cat ca
'     hai doan tai giao diem.
'   - Cac dinh gan nhau (< tol) gop ve 1 toa do.
'============================================================
Public Function NoiDoanGiao(ByVal segs As Collection, ByVal tol As Double) As Collection
    Dim n As Long, i As Long, j As Long, s() As Double
    n = segs.Count
    If n = 0 Then Set NoiDoanGiao = segs: Exit Function
    If tol <= 0 Then tol = 0.001
    Dim ax() As Double, ay() As Double, bx() As Double, by() As Double, dl() As Double
    ReDim ax(1 To n): ReDim ay(1 To n): ReDim bx(1 To n): ReDim by(1 To n): ReDim dl(1 To n)
    Dim tongL As Double
    For i = 1 To n
        s = segs.Item(i)
        ax(i) = s(0): ay(i) = s(1): bx(i) = s(2): by(i) = s(3)
        dl(i) = Sqr((bx(i) - ax(i)) ^ 2 + (by(i) - ay(i)) ^ 2)
        tongL = tongL + dl(i)
    Next i

    Dim tL() As Collection
    ReDim tL(1 To n)
    For i = 1 To n
        Set tL(i) = New Collection
        tL(i).Add Array(0#, ax(i), ay(i))
        tL(i).Add Array(1#, bx(i), by(i))
    Next i

    LuoiGiaoCat n, ax, ay, bx, by, dl, tol, tL

    ' gop dinh gan nhau (luoi o = tol) roi xuat doan con
    Dim p As Long
    Dim nut As Object, kq As New Collection, arr() As Variant, na As Long, r As Long, tmp As Variant
    Dim p1x As Double, p1y As Double, p2x As Double, p2y As Double
    Set nut = CreateObject("Scripting.Dictionary")
    For i = 1 To n
        If dl(i) <= tol Then GoTo TiepK
        na = tL(i).Count
        ReDim arr(1 To na)
        For p = 1 To na
            arr(p) = tL(i).Item(p)
        Next p
        For p = 2 To na
            tmp = arr(p): r = p - 1
            Do While r >= 1
                If arr(r)(0) > tmp(0) Then arr(r + 1) = arr(r): r = r - 1 Else Exit Do
            Loop
            arr(r + 1) = tmp
        Next p
        NutChuan arr(1)(1), arr(1)(2), tol, nut, p1x, p1y
        For p = 2 To na
            NutChuan arr(p)(1), arr(p)(2), tol, nut, p2x, p2y
            If Abs(p2x - p1x) + Abs(p2y - p1y) > tol * 0.01 Then
                kq.Add NewSeg(p1x, p1y, p2x, p2y)
                p1x = p2x: p1y = p2y
            End If
        Next p
TiepK:
    Next i
    Set NoiDoanGiao = kq
End Function

Private Sub GiaoCap(ByVal i As Long, ByVal j As Long, ax() As Double, ay() As Double, _
                    bx() As Double, by() As Double, dl() As Double, ByVal tol As Double, tL() As Collection)
    Dim d1x As Double, d1y As Double, d2x As Double, d2y As Double, den As Double
    Dim wx As Double, wy As Double, t As Double, u As Double, eT As Double, eU As Double
    Dim px As Double, py As Double
    If dl(i) <= tol Or dl(j) <= tol Then Exit Sub
    If LonHon(ax(i), bx(i)) + tol < NhoHon(ax(j), bx(j)) Then Exit Sub
    If LonHon(ax(j), bx(j)) + tol < NhoHon(ax(i), bx(i)) Then Exit Sub
    If LonHon(ay(i), by(i)) + tol < NhoHon(ay(j), by(j)) Then Exit Sub
    If LonHon(ay(j), by(j)) + tol < NhoHon(ay(i), by(i)) Then Exit Sub
    d1x = bx(i) - ax(i): d1y = by(i) - ay(i)
    d2x = bx(j) - ax(j): d2y = by(j) - ay(j)
    den = d1x * d2y - d1y * d2x
    eT = tol / dl(i): eU = tol / dl(j)
    If Abs(den) <= 0.000000001 * dl(i) * dl(j) Then
        DiemTrenDoan tL(i), ax(i), ay(i), d1x, d1y, dl(i), ax(j), ay(j), tol
        DiemTrenDoan tL(i), ax(i), ay(i), d1x, d1y, dl(i), bx(j), by(j), tol
        DiemTrenDoan tL(j), ax(j), ay(j), d2x, d2y, dl(j), ax(i), ay(i), tol
        DiemTrenDoan tL(j), ax(j), ay(j), d2x, d2y, dl(j), bx(i), by(i), tol
        Exit Sub
    End If
    wx = ax(j) - ax(i): wy = ay(j) - ay(i)
    t = (wx * d2y - wy * d2x) / den
    u = (wx * d1y - wy * d1x) / den
    If t < -eT Or t > 1# + eT Or u < -eU Or u > 1# + eU Then Exit Sub
    ' hai dau mut trung nhau: khong can cat
    If (t <= eT Or t >= 1# - eT) And (u <= eU Or u >= 1# - eU) Then Exit Sub
    If t <= eT Then
        px = ax(i): py = ay(i): t = 0#
    ElseIf t >= 1# - eT Then
        px = bx(i): py = by(i): t = 1#
    ElseIf u <= eU Then
        px = ax(j): py = ay(j)
    ElseIf u >= 1# - eU Then
        px = bx(j): py = by(j)
    Else
        px = ax(i) + t * d1x: py = ay(i) + t * d1y
    End If
    If u < 0# Then u = 0#
    If u > 1# Then u = 1#
    If t < 0# Then t = 0#
    If t > 1# Then t = 1#
    If u <= eU Then
        u = 0#
    ElseIf u >= 1# - eU Then
        u = 1#
    End If
    tL(i).Add Array(t, px, py)
    tL(j).Add Array(u, px, py)
End Sub

Private Sub DiemTrenDoan(ByVal tL As Collection, ByVal ox As Double, ByVal oy As Double, _
                         ByVal dx As Double, ByVal dy As Double, ByVal dd As Double, _
                         ByVal qx As Double, ByVal qy As Double, ByVal tol As Double)
    Dim t As Double, kc As Double
    If dd <= 0 Then Exit Sub
    t = ((qx - ox) * dx + (qy - oy) * dy) / (dd * dd)
    kc = Abs((qx - ox) * dy - (qy - oy) * dx) / dd
    If kc <= tol And t > tol / dd And t < 1# - tol / dd Then tL.Add Array(t, qx, qy)
End Sub


' Tim moi diem cat giua n doan (luoi o vuong). tL(i) da co san 2 dau mut,
' them Array(t, x, y) cho moi diem cat tren doan i.
Public Sub LuoiGiaoCat(ByVal n As Long, ax() As Double, ay() As Double, bx() As Double, by() As Double, _
                       dl() As Double, ByVal tol As Double, tL() As Collection)
    Dim i As Long, tongL As Double
    For i = 1 To n
        tongL = tongL + dl(i)
    Next i
    If n = 0 Then Exit Sub
    ' luoi: o = 2 lan chieu dai doan trung binh
    Dim oL As Double
    oL = tongL / n * 2#
    If oL < tol * 20# Then oL = tol * 20#
    Dim luoi As Object, key As String, gx1 As Long, gy1 As Long, gx2 As Long, gy2 As Long, gx As Long, gy As Long
    Set luoi = CreateObject("Scripting.Dictionary")
    For i = 1 To n
        If dl(i) > tol Then
            gx1 = Int((NhoHon(ax(i), bx(i)) - tol) / oL): gx2 = Int((LonHon(ax(i), bx(i)) + tol) / oL)
            gy1 = Int((NhoHon(ay(i), by(i)) - tol) / oL): gy2 = Int((LonHon(ay(i), by(i)) + tol) / oL)
            ' SUA 08/11: nhan bang Double - doan rat dai (vd net lac ve goc toa do) lam Long tran so (loi 6)
            If CDbl(gx2 - gx1 + 1) * CDbl(gy2 - gy1 + 1) <= 2500# Then
                For gx = gx1 To gx2
                    For gy = gy1 To gy2
                        key = gx & "|" & gy
                        If Not luoi.Exists(key) Then luoi.Add key, New Collection
                        luoi(key).Add i
                    Next gy
                Next gx
            Else
                key = "lon"                         ' doan qua dai: kiem voi tat ca
                If Not luoi.Exists(key) Then luoi.Add key, New Collection
                luoi(key).Add i
            End If
        End If
    Next i

    ' cap doan trong cung o (moi cap chi xet 1 lan)
    Dim kk As Variant, dS As Collection, p As Long, q As Long, a As Long, b As Long, nP As Long
    Dim daXet As Object, kp As String
    Set daXet = CreateObject("Scripting.Dictionary")
    For Each kk In luoi.Keys
        Set dS = luoi(kk)
        nP = dS.Count
        If kk = "lon" Then
            ' doan qua dai: kiem voi moi doan khac
            For p = 1 To nP
                a = dS.Item(p)
                For b = 1 To n
                    If b <> a Then
                        If a < b Then kp = a & "|" & b Else kp = b & "|" & a
                        If Not daXet.Exists(kp) Then
                            daXet.Add kp, True
                            GiaoCap a, b, ax, ay, bx, by, dl, tol, tL
                        End If
                    End If
                Next b
            Next p
        Else
            For p = 1 To nP - 1
                For q = p + 1 To nP
                    a = dS.Item(p): b = dS.Item(q)
                    If a < b Then kp = a & "|" & b Else kp = b & "|" & a
                    If Not daXet.Exists(kp) Then
                        daXet.Add kp, True
                        GiaoCap a, b, ax, ay, bx, by, dl, tol, tL
                    End If
                Next q
            Next p
        End If
    Next kk

End Sub

' Gop dinh: tra ve toa do dinh da co trong pham vi tol (luoi o = tol, xet 3x3 o)
Public Sub NutChuan(ByVal x As Double, ByVal y As Double, ByVal tol As Double, _
                     ByVal nut As Object, ByRef rx As Double, ByRef ry As Double)
    Dim gx As Long, gy As Long, dx As Long, dy As Long, key As String, c As Collection, i As Long, p As Variant
    gx = Int(x / tol): gy = Int(y / tol)
    For dx = -1 To 1
        For dy = -1 To 1
            key = (gx + dx) & "|" & (gy + dy)
            If nut.Exists(key) Then
                Set c = nut(key)
                For i = 1 To c.Count
                    p = c.Item(i)
                    If Abs(p(0) - x) <= tol And Abs(p(1) - y) <= tol Then rx = p(0): ry = p(1): Exit Sub
                Next i
            End If
        Next dy
    Next dx
    key = gx & "|" & gy
    If Not nut.Exists(key) Then nut.Add key, New Collection
    nut(key).Add Array(x, y)
    rx = x: ry = y
End Sub

Private Function LonHon(ByVal a As Double, ByVal b As Double) As Double
    If a > b Then LonHon = a Else LonHon = b
End Function
Private Function NhoHon(ByVal a As Double, ByVal b As Double) As Double
    If a < b Then NhoHon = a Else NhoHon = b
End Function

'============================================================
' CHUAN HOA THU TU DINH (quy tac danh so dinh thua):
'   bat dau tu dinh TREN - TRAI (gan goc tren trai khung bao nhat),
'   di theo chieu KIM DONG HO (trai -> phai o canh tren, roi xuong duoi).
'   Ap dung ca vong ngoai va cac vong dao.
'============================================================
Public Sub ChuanHoaVong(ByVal v As clsVung)
    Dim rg() As Double, k As Long
    If v Is Nothing Then Exit Sub
    If Not v.HasRing Then Exit Sub
    Dim r2() As Double
    rg = v.ring
    r2 = VongTrenTraiCW(rg)
    v.ring = r2
    If v.dao Is Nothing Then Exit Sub
    If v.dao.Count = 0 Then Exit Sub
    Dim moi As New Collection
    For k = 1 To v.dao.Count
        rg = v.dao.Item(k)
        moi.Add VongTrenTraiCW(rg)
    Next k
    Set v.dao = moi
End Sub

Public Function VongTrenTraiCW(rg() As Double) As Double()
    Dim m As Long, i As Long, a As Double, kq() As Double
    m = UBound(rg, 1)                       ' rg(m) = rg(0)
    If m < 3 Then VongTrenTraiCW = rg: Exit Function
    ' chieu: dien tich co dau > 0 = nguoc kim dong ho -> dao lai
    For i = 0 To m - 1
        a = a + rg(i, 0) * rg(i + 1, 1) - rg(i + 1, 0) * rg(i, 1)
    Next i
    Dim tmp() As Double
    ReDim tmp(0 To m - 1, 0 To 1)
    For i = 0 To m - 1
        If a > 0 Then
            tmp(i, 0) = rg(m - 1 - i, 0): tmp(i, 1) = rg(m - 1 - i, 1)
        Else
            tmp(i, 0) = rg(i, 0): tmp(i, 1) = rg(i, 1)
        End If
    Next i
    ' dinh gan goc tren-trai cua khung bao nhat (khoang cach chuan hoa)
    Dim x1 As Double, x2 As Double, y1 As Double, y2 As Double, w As Double, h As Double
    x1 = tmp(0, 0): x2 = x1: y1 = tmp(0, 1): y2 = y1
    For i = 1 To m - 1
        If tmp(i, 0) < x1 Then x1 = tmp(i, 0)
        If tmp(i, 0) > x2 Then x2 = tmp(i, 0)
        If tmp(i, 1) < y1 Then y1 = tmp(i, 1)
        If tmp(i, 1) > y2 Then y2 = tmp(i, 1)
    Next i
    w = x2 - x1: h = y2 - y1
    If w <= 0 Then w = 1
    If h <= 0 Then h = 1
    Dim best As Long, d As Double, dmin As Double
    dmin = 1E+30
    For i = 0 To m - 1
        d = ((tmp(i, 0) - x1) / w) ^ 2 + ((y2 - tmp(i, 1)) / h) ^ 2
        If d < dmin - 0.0000001 Then dmin = d: best = i
    Next i
    ReDim kq(0 To m, 0 To 1)
    For i = 0 To m - 1
        kq(i, 0) = tmp((i + best) Mod m, 0): kq(i, 1) = tmp((i + best) Mod m, 1)
    Next i
    kq(m, 0) = kq(0, 0): kq(m, 1) = kq(0, 1)
    VongTrenTraiCW = kq
End Function

'============================================================
' SUA 08/11: kiem tra toa do hop le (net hong co toa do NaN / vo cuc
'   -> Int()/CLng() bao loi 6 Overflow). Dung truoc khi dua dinh vao tinh toan.
'============================================================
Public Function DC_SoHopLe(ByVal v As Double) As Boolean
    On Error GoTo Hong
    If InStr(CStr(v), "#") > 0 Then Exit Function
    If Abs(v) < 1000000000000# Then DC_SoHopLe = True
    Exit Function
Hong:
    DC_SoHopLe = False
End Function

Public Function DC_DinhHopLe(pts() As Point3d) As Boolean
    Dim i As Long
    On Error GoTo Hong
    For i = LBound(pts) To UBound(pts)
        If Not DC_SoHopLe(pts(i).x) Then Exit Function
        If Not DC_SoHopLe(pts(i).y) Then Exit Function
    Next i
    DC_DinhHopLe = True
    Exit Function
Hong:
    DC_DinhHopLe = False
End Function

Attribute VB_Name = "modKTT"
'============================================================
' modKTT - Chon tinh -> kinh tuyen truc VN-2000 (mui 3 do) truoc khi xem ve tinh
'   Bang KTT theo Thong tu 973/2001/TT-TCDC (63 tinh cu). Sau sap nhap 2025,
'   1 tinh moi co the gom nhieu vung cu KHAC KTT (vd Vinh Long: Vinh Long,
'   Tra Vinh 105 30 ; Ben Tre 105 45) -> chon dung VUNG CU cua ban do.
'   Ghi ini KTT (modVeTinh doc) + KTT_TINH (nho lua chon).
'============================================================
Option Explicit

Public gKTTViec As String       ' "VETINH" / "GEARTH"

Public Sub DC_MoChonKTT(ByVal viec As String)
    gKTTViec = viec
    DC_MoFormTuTao "frmChonKTT"
End Sub

' Moi phan tu: Array(nhan, ktt)
Public Function KTT_DanhSach() As Collection
    Dim c As New Collection
    c.Add Array("An Giang (104" & ChrW(176) & "45')", 104.75)
    c.Add Array("An Giang - v" & ChrW(249) & "ng Ki" & ChrW(234) & "n Giang c" & ChrW(361) & " (104" & ChrW(176) & "30')", 104.5)
    c.Add Array("B" & ChrW(7855) & "c Ninh (105" & ChrW(176) & "30')", 105.5)
    c.Add Array("B" & ChrW(7855) & "c Ninh - v" & ChrW(249) & "ng B" & ChrW(7855) & "c Giang c" & ChrW(361) & " (107" & ChrW(176) & "00')", 107#)
    c.Add Array("Cao B" & ChrW(7857) & "ng (105" & ChrW(176) & "45')", 105.75)
    c.Add Array("C" & ChrW(224) & " Mau (104" & ChrW(176) & "30')", 104.5)
    c.Add Array("C" & ChrW(224) & " Mau - v" & ChrW(249) & "ng B" & ChrW(7841) & "c Li" & ChrW(234) & "u c" & ChrW(361) & " (105" & ChrW(176) & "00')", 105#)
    c.Add Array("C" & ChrW(7847) & "n Th" & ChrW(417) & " (105" & ChrW(176) & "00')", 105#)
    c.Add Array("C" & ChrW(7847) & "n Th" & ChrW(417) & " - v" & ChrW(249) & "ng H" & ChrW(7853) & "u Giang c" & ChrW(361) & " (105" & ChrW(176) & "00')", 105#)
    c.Add Array("C" & ChrW(7847) & "n Th" & ChrW(417) & " - v" & ChrW(249) & "ng S" & ChrW(243) & "c Tr" & ChrW(259) & "ng c" & ChrW(361) & " (105" & ChrW(176) & "30')", 105.5)
    c.Add Array("Gia Lai (108" & ChrW(176) & "30')", 108.5)
    c.Add Array("Gia Lai - v" & ChrW(249) & "ng B" & ChrW(236) & "nh " & ChrW(272) & ChrW(7883) & "nh c" & ChrW(361) & " (108" & ChrW(176) & "15')", 108.25)
    c.Add Array("H" & ChrW(224) & " N" & ChrW(7897) & "i (105" & ChrW(176) & "00')", 105#)
    c.Add Array("H" & ChrW(224) & " T" & ChrW(297) & "nh (105" & ChrW(176) & "30')", 105.5)
    c.Add Array("H" & ChrW(432) & "ng Y" & ChrW(234) & "n (105" & ChrW(176) & "30')", 105.5)
    c.Add Array("H" & ChrW(432) & "ng Y" & ChrW(234) & "n - v" & ChrW(249) & "ng Th" & ChrW(225) & "i B" & ChrW(236) & "nh c" & ChrW(361) & " (105" & ChrW(176) & "30')", 105.5)
    c.Add Array("H" & ChrW(7843) & "i Ph" & ChrW(242) & "ng (105" & ChrW(176) & "45')", 105.75)
    c.Add Array("H" & ChrW(7843) & "i Ph" & ChrW(242) & "ng - v" & ChrW(249) & "ng H" & ChrW(7843) & "i D" & ChrW(432) & ChrW(417) & "ng c" & ChrW(361) & " (105" & ChrW(176) & "30')", 105.5)
    c.Add Array("Kh" & ChrW(225) & "nh H" & ChrW(242) & "a (108" & ChrW(176) & "15')", 108.25)
    c.Add Array("Kh" & ChrW(225) & "nh H" & ChrW(242) & "a - v" & ChrW(249) & "ng Ninh Thu" & ChrW(7853) & "n c" & ChrW(361) & " (108" & ChrW(176) & "15')", 108.25)
    c.Add Array("Lai Ch" & ChrW(226) & "u (103" & ChrW(176) & "00')", 103#)
    c.Add Array("L" & ChrW(224) & "o Cai (104" & ChrW(176) & "45')", 104.75)
    c.Add Array("L" & ChrW(224) & "o Cai - v" & ChrW(249) & "ng Y" & ChrW(234) & "n B" & ChrW(225) & "i c" & ChrW(361) & " (104" & ChrW(176) & "45')", 104.75)
    c.Add Array("L" & ChrW(226) & "m " & ChrW(272) & ChrW(7891) & "ng (107" & ChrW(176) & "45')", 107.75)
    c.Add Array("L" & ChrW(226) & "m " & ChrW(272) & ChrW(7891) & "ng - v" & ChrW(249) & "ng B" & ChrW(236) & "nh Thu" & ChrW(7853) & "n c" & ChrW(361) & " (108" & ChrW(176) & "30')", 108.5)
    c.Add Array("L" & ChrW(226) & "m " & ChrW(272) & ChrW(7891) & "ng - v" & ChrW(249) & "ng " & ChrW(272) & ChrW(7855) & "k N" & ChrW(244) & "ng c" & ChrW(361) & " (108" & ChrW(176) & "30')", 108.5)
    c.Add Array("L" & ChrW(7841) & "ng S" & ChrW(417) & "n (107" & ChrW(176) & "15')", 107.25)
    c.Add Array("Ngh" & ChrW(7879) & " An (104" & ChrW(176) & "45')", 104.75)
    c.Add Array("Ninh B" & ChrW(236) & "nh (105" & ChrW(176) & "00')", 105#)
    c.Add Array("Ninh B" & ChrW(236) & "nh - v" & ChrW(249) & "ng H" & ChrW(224) & " Nam c" & ChrW(361) & " (105" & ChrW(176) & "00')", 105#)
    c.Add Array("Ninh B" & ChrW(236) & "nh - v" & ChrW(249) & "ng Nam " & ChrW(272) & ChrW(7883) & "nh c" & ChrW(361) & " (105" & ChrW(176) & "30')", 105.5)
    c.Add Array("Ph" & ChrW(250) & " Th" & ChrW(7885) & " (104" & ChrW(176) & "45')", 104.75)
    c.Add Array("Ph" & ChrW(250) & " Th" & ChrW(7885) & " - v" & ChrW(249) & "ng H" & ChrW(242) & "a B" & ChrW(236) & "nh c" & ChrW(361) & " (106" & ChrW(176) & "00')", 106#)
    c.Add Array("Ph" & ChrW(250) & " Th" & ChrW(7885) & " - v" & ChrW(249) & "ng V" & ChrW(297) & "nh Ph" & ChrW(250) & "c c" & ChrW(361) & " (105" & ChrW(176) & "00')", 105#)
    c.Add Array("Qu" & ChrW(7843) & "ng Ng" & ChrW(227) & "i (108" & ChrW(176) & "00')", 108#)
    c.Add Array("Qu" & ChrW(7843) & "ng Ng" & ChrW(227) & "i - v" & ChrW(249) & "ng Kon Tum c" & ChrW(361) & " (107" & ChrW(176) & "30')", 107.5)
    c.Add Array("Qu" & ChrW(7843) & "ng Ninh (107" & ChrW(176) & "45')", 107.75)
    c.Add Array("Qu" & ChrW(7843) & "ng Tr" & ChrW(7883) & " (106" & ChrW(176) & "15')", 106.25)
    c.Add Array("Qu" & ChrW(7843) & "ng Tr" & ChrW(7883) & " - v" & ChrW(249) & "ng Qu" & ChrW(7843) & "ng B" & ChrW(236) & "nh c" & ChrW(361) & " (106" & ChrW(176) & "00')", 106#)
    c.Add Array("S" & ChrW(417) & "n La (104" & ChrW(176) & "00')", 104#)
    c.Add Array("TP H" & ChrW(7891) & " Ch" & ChrW(237) & " Minh (105" & ChrW(176) & "45')", 105.75)
    c.Add Array("TP H" & ChrW(7891) & " Ch" & ChrW(237) & " Minh - v" & ChrW(249) & "ng B" & ChrW(224) & " R" & ChrW(7883) & "a - V" & ChrW(361) & "ng T" & ChrW(224) & "u c" & ChrW(361) & " (107" & ChrW(176) & "45')", 107.75)
    c.Add Array("TP H" & ChrW(7891) & " Ch" & ChrW(237) & " Minh - v" & ChrW(249) & "ng B" & ChrW(236) & "nh D" & ChrW(432) & ChrW(417) & "ng c" & ChrW(361) & " (105" & ChrW(176) & "45')", 105.75)
    c.Add Array("Thanh H" & ChrW(243) & "a (105" & ChrW(176) & "00')", 105#)
    c.Add Array("Th" & ChrW(225) & "i Nguy" & ChrW(234) & "n (106" & ChrW(176) & "30')", 106.5)
    c.Add Array("Th" & ChrW(225) & "i Nguy" & ChrW(234) & "n - v" & ChrW(249) & "ng B" & ChrW(7855) & "c K" & ChrW(7841) & "n c" & ChrW(361) & " (106" & ChrW(176) & "30')", 106.5)
    c.Add Array("Th" & ChrW(7915) & "a Thi" & ChrW(234) & "n Hu" & ChrW(7871) & " (107" & ChrW(176) & "00')", 107#)
    c.Add Array("Tuy" & ChrW(234) & "n Quang (106" & ChrW(176) & "00')", 106#)
    c.Add Array("Tuy" & ChrW(234) & "n Quang - v" & ChrW(249) & "ng H" & ChrW(224) & " Giang c" & ChrW(361) & " (105" & ChrW(176) & "30')", 105.5)
    c.Add Array("T" & ChrW(226) & "y Ninh (105" & ChrW(176) & "30')", 105.5)
    c.Add Array("T" & ChrW(226) & "y Ninh - v" & ChrW(249) & "ng Long An c" & ChrW(361) & " (105" & ChrW(176) & "45')", 105.75)
    c.Add Array("V" & ChrW(297) & "nh Long (105" & ChrW(176) & "30')", 105.5)
    c.Add Array("V" & ChrW(297) & "nh Long - v" & ChrW(249) & "ng B" & ChrW(7871) & "n Tre c" & ChrW(361) & " (105" & ChrW(176) & "45')", 105.75)
    c.Add Array("V" & ChrW(297) & "nh Long - v" & ChrW(249) & "ng Tr" & ChrW(224) & " Vinh c" & ChrW(361) & " (105" & ChrW(176) & "30')", 105.5)
    c.Add Array(ChrW(272) & "i" & ChrW(7879) & "n Bi" & ChrW(234) & "n (103" & ChrW(176) & "00')", 103#)
    c.Add Array(ChrW(272) & ChrW(224) & " N" & ChrW(7861) & "ng (107" & ChrW(176) & "45')", 107.75)
    c.Add Array(ChrW(272) & ChrW(224) & " N" & ChrW(7861) & "ng - v" & ChrW(249) & "ng Qu" & ChrW(7843) & "ng Nam c" & ChrW(361) & " (107" & ChrW(176) & "45')", 107.75)
    c.Add Array(ChrW(272) & ChrW(7855) & "k L" & ChrW(7855) & "k (108" & ChrW(176) & "30')", 108.5)
    c.Add Array(ChrW(272) & ChrW(7855) & "k L" & ChrW(7855) & "k - v" & ChrW(249) & "ng Ph" & ChrW(250) & " Y" & ChrW(234) & "n c" & ChrW(361) & " (108" & ChrW(176) & "30')", 108.5)
    c.Add Array(ChrW(272) & ChrW(7891) & "ng Nai (107" & ChrW(176) & "45')", 107.75)
    c.Add Array(ChrW(272) & ChrW(7891) & "ng Nai - v" & ChrW(249) & "ng B" & ChrW(236) & "nh Ph" & ChrW(432) & ChrW(7899) & "c c" & ChrW(361) & " (106" & ChrW(176) & "15')", 106.25)
    c.Add Array(ChrW(272) & ChrW(7891) & "ng Th" & ChrW(225) & "p (105" & ChrW(176) & "00')", 105#)
    c.Add Array(ChrW(272) & ChrW(7891) & "ng Th" & ChrW(225) & "p - v" & ChrW(249) & "ng Ti" & ChrW(7873) & "n Giang c" & ChrW(361) & " (105" & ChrW(176) & "45')", 105.75)
    Set KTT_DanhSach = c
End Function

Public Sub KTT_ChayViec(ByVal ktt As Double, ByVal datum7 As Boolean, ByVal viec As String)
    DC_GhiCauHinh "KTT", Replace(CStr(ktt), ",", ".")
    DC_GhiCauHinh "DATUM7", IIf(datum7, "1", "0")
    If viec = "GEARTH" Then DC_MoGoogleEarth Else DC_XemVeTinh
End Sub

Attribute VB_Name = "modKhungMau"
Option Explicit

' TY LE Width/Height cua chu - DO TU BAN gCadas:
'   Height = 0.7000 ; Width = 0.5417  ->  0.5417 / 0.7 = 0.774
' Code cu dat TextStyle.Width = Height (tuc ty le 1.0) nen moi chu bi keo
' rong ~29% so voi gCadas -> so trong bang tran ra khoi cot.
Private Const C_TILE_W As Double = 0.774

' Ty le to ban do lan truoc (nho de lan sau khong phai go lai).
Private gTyLeCu As Double

' Tam X va be rong 4 cot bang muc 8 (toa do TEMPLATE), do tu luoi ke DOC
' (level 60): 117683.0 | 117757.7 | 117926.5 | 118102.0 | 118372.8
'   Dinh 117683..117757.7 | X 117757.7..117926.5 | Y 117926.5..118102 | Canh 118102..118372.8
' Dat chu vao TAM cot -> thang hang duoi tieu de. Neu doi mau thi sua 8 so nay.
' SUA 08/10/2026: chuyen tu Const sang bien. Mau cu (TrichLucBanDo_mau.txt)
' dung dung 8 so goc duoi day (DatCotMacDinh). Mau bat tu file .dgn (dong H
' co co "DGN") thi TINH LAI tu luoi ke doc cua bang + vi tri tag (TinhCotTuLuoi).
Private CX_DINH As Double, CX_X As Double, CX_Y As Double, CX_CANH As Double
Private CW_DINH As Double, CW_X As Double, CW_Y As Double, CW_CANH As Double
Private gTuDgn As Boolean, gCotDgn As Boolean
Private gScDgn As Double, gDgnPath As String     ' chep thang phan tu tu file mau .dgn
' Vi tri tam o so do cua lan trich luc vua ve (modMoTrichLuc dung de zoom)
Public gTLCx As Double, gTLCy As Double
' True = ty le khung chon Tu dong (duoc thu nho so do neu thua qua lon)
Public gTyLeTuDong As Boolean

' Sau khi Width dung ty le, RongChuoi() uoc luong gan dung thuc te.
' Chi giu chut bien an toan. Chu con tran -> tang; chu bi thu nho oan -> giam.
Private Const C_CAL As Double = 1.05

' GHI CHU cot bang muc 8 / quy uoc X-Y: xem ban luu truoc 15/10/2026.

'============================================================
' modKhungMau - Chen khung mau Phu luc 19 (TT26) + dien tag
' Doc file phang TrichLucBanDo_mau.txt (chuyen tu .mau.json).
'============================================================

Private gUor As Double
Private gXmin As Double, gYmin As Double, gXmax As Double, gYmax As Double
Private gNL As Long
Private gLineLevel() As Long
Private gLineCoords() As Variant   ' moi phan tu: Double() = x0,y0,x1,y1,...
Private gNT As Long
Private gTL() As Long, gTCao() As Double, gTX() As Double, gTY() As Double
Private gTKind() As String, gTS() As String
Private gLoaded As Boolean
Private gKieuCan As String   ' "T" = layout trai ; "G" = giua
' Level so do (canh thua / so hieu dinh / nhan) + level so lieu bang toa do
Private mLvBang As Level, mLvRanh As Level, mLvSo As Level, mLvNhan As Level


' Doc so an toan (luon dung dau ".")
Private Function ValD(ByVal s As String) As Double
    ValD = val(s)
End Function

Private Function NapMau(ByVal path As String) As Boolean
    NapMau = False
    gTuDgn = False
    Dim st As Object
    On Error Resume Next
    Set st = CreateObject("ADODB.Stream")
    On Error GoTo 0
    If st Is Nothing Then Exit Function

    st.Type = 2
    st.Charset = "utf-8"
    st.Open
    On Error Resume Next
    st.LoadFromFile path
    If Err.Number <> 0 Then st.Close: Exit Function
    On Error GoTo 0
    Dim txt As String
    txt = st.ReadText(-1)
    st.Close

    Dim raw() As String
    raw = Split(txt, vbLf)

    ' Dem
    Dim i As Long, nL As Long, nt As Long
    For i = LBound(raw) To UBound(raw)
        If Len(raw(i)) > 0 Then
            Select Case Left$(raw(i), 1)
                Case "L": nL = nL + 1
                Case "T": nt = nt + 1
            End Select
        End If
    Next i
    ReDim gLineLevel(1 To nL + 1)
    ReDim gLineCoords(1 To nL + 1)
    ReDim gTL(1 To nt + 1)
    ReDim gTKind(1 To nt + 1)
    ReDim gTCao(1 To nt + 1)
    ReDim gTX(1 To nt + 1)
    ReDim gTY(1 To nt + 1)
    ReDim gTS(1 To nt + 1)
    gNL = 0: gNT = 0

    Dim parts() As String, k As Long, m As Long
    Dim co() As Double
    For i = LBound(raw) To UBound(raw)
        If Len(raw(i)) = 0 Then GoTo tiep
        parts = Split(raw(i), vbTab)
        Select Case parts(0)
            Case "H"
                gUor = ValD(parts(1))
                If UBound(parts) >= 6 Then gTuDgn = (Trim$(parts(6)) = "DGN")
                gScDgn = 0: gDgnPath = ""
                If gTuDgn And UBound(parts) >= 8 Then
                    gScDgn = ValD(parts(7)): gDgnPath = Trim$(parts(8))
                End If
                gXmin = ValD(parts(2)): gYmin = ValD(parts(3))
                gXmax = ValD(parts(4)): gYmax = ValD(parts(5))
            Case "L"
                gNL = gNL + 1
                gLineLevel(gNL) = CLng(ValD(parts(1)))
                m = UBound(parts) - 1        ' so gia tri toa do
                ReDim co(0 To m - 1)
                For k = 0 To m - 1
                    co(k) = ValD(parts(2 + k))
                Next k
                gLineCoords(gNL) = co
            Case "T"
                gNT = gNT + 1
                gTL(gNT) = CLng(ValD(parts(1)))
                gTKind(gNT) = parts(2)
                gTCao(gNT) = ValD(parts(3))
                gTX(gNT) = ValD(parts(4))
                gTY(gNT) = ValD(parts(5))
                If UBound(parts) >= 6 Then gTS(gNT) = parts(6) Else gTS(gNT) = ""
        End Select
tiep:
    Next i

    DatCotMacDinh
    gCotDgn = False
    If gTuDgn Then TinhCotTuLuoi
    gLoaded = True
    NapMau = True
End Function

' Tim o so do (level 24) -> tra ve tam & kich thuoc qua ByRef
Private Function TimBox(ByRef cxb As Double, ByRef cyb As Double, _
                        ByRef bw As Double, ByRef bh As Double) As Boolean
    Dim i As Long, j As Long, co() As Double, m As Long
    Dim x1 As Double, y1 As Double, x2 As Double, y2 As Double
    Dim bestA As Double, has As Boolean
    bestA = -1: has = False
    For i = 1 To gNL
        If gLineLevel(i) = 24 Then
            co = gLineCoords(i)
            m = (UBound(co) + 1) \ 2
            x1 = co(0): x2 = co(0): y1 = co(1): y2 = co(1)
            For j = 0 To m - 1
                If co(2 * j) < x1 Then x1 = co(2 * j)
                If co(2 * j) > x2 Then x2 = co(2 * j)
                If co(2 * j + 1) < y1 Then y1 = co(2 * j + 1)
                If co(2 * j + 1) > y2 Then y2 = co(2 * j + 1)
            Next j
            If (x2 - x1) * (y2 - y1) > bestA Then
                bestA = (x2 - x1) * (y2 - y1)
                cxb = (x1 + x2) / 2#: cyb = (y1 + y2) / 2#
                bw = x2 - x1: bh = y2 - y1
                has = True
            End If
        End If
    Next i
    TimBox = has
End Function

Private Function TenLevelActive() As String
    On Error Resume Next
    TenLevelActive = ActiveSettings.Level.Name
    On Error GoTo 0
End Function

' Dinh dang so kieu VN (dau phay), so le nl
Private Function FNum(ByVal v As Double, ByVal nL As Long) As String
    Dim f As String
    If nL <= 0 Then f = "0" Else f = "0." & String$(nL, "0")
    FNum = Replace(Format$(v, f), ".", ",")
End Function


'============================================================
' LENH: CHEN KHUNG MAU PHU LUC 19
'============================================================
Public Sub DC_ChenKhungMau()
    ' SUA 11/10/2026: lenh cu (hoi tung buoc) da thay bang form Trich luc
    DC_MoTrichLuc
End Sub


' Gia tri cho tung tag
Private Function GiaTriTag(ByVal tag As String, ByVal v As clsVung, _
                           ByVal toBanDo As String, ByVal tenXa As String, _
                           ByVal tenHuyen As String, ByVal tenTinh As String, _
                           ByVal slDT As Long) As String
    Select Case tag
        Case "soHieuThua": GiaTriTag = v.soThua
        Case "toBanDo":    GiaTriTag = toBanDo
        Case "dienTich":   GiaTriTag = FNum(v.dt, slDT)
        Case "mdsd":       GiaTriTag = v.loaiDat
        Case "chuSuDung":  GiaTriTag = v.TenChu
        Case "tenXa":      GiaTriTag = tenXa
        Case "tenHuyen":   GiaTriTag = tenHuyen
        Case "tenTinh":    GiaTriTag = tenTinh
        Case "B":          GiaTriTag = "B"
        Case "2":          GiaTriTag = "2"
        Case Else:         GiaTriTag = ""
    End Select
End Function

' Tra ve min(hHienTai, co chu lon nhat ma chuoi s van vua be rong wMax).
' Dung de tim MOT co chu chung cho ca bang thay vi thu nho tung o.
Private Function CaoVuaO(ByVal hHienTai As Double, ByVal s As String, _
                         ByVal hGoc As Double, ByVal wMax As Double) As Double
    CaoVuaO = hHienTai
    If wMax <= 0# Or Len(s) = 0 Then Exit Function
    Dim w As Double, h As Double
    w = RongChuoi(s, hGoc) * C_CAL
    h = hGoc
    If w > wMax * 0.9 Then h = hGoc * (wMax * 0.9) / w
    If h < hHienTai Then CaoVuaO = h
End Function

' Dien 1 cell bang. tx = TAM X cot (template), ty = TAM Y hang (template).
' SUA 05/08/2026: dat chu CANH GIUA O bang Justification CenterCenter -> chu
' luon nam giua cot (thang hang duoi tieu de), khong con lech phai nhu cu.
' wMax chi de THU NHO chu neu rong hon o.
Private Sub DienCell(ByVal tX As Double, ByVal ty As Double, ByVal s As String, _
                     ByVal hc As Double, ByVal cxb As Double, ByVal cyb As Double, _
                     ByVal k As Double, ByVal Cpx As Double, ByVal Cpy As Double, _
                     Optional ByVal wMax As Double = 0#)
    If Len(Trim$(s)) = 0 Then Exit Sub
    Dim mx As Double, my As Double, h As Double, w As Double
    mx = (tX - cxb) * k + Cpx           ' tam o (da map sang ban ve)
    my = (ty - cyb) * k + Cpy
    h = hc
    w = RongChuoi(s, h) * C_CAL
    If wMax > 0# And w > wMax * 0.9 Then h = h * (wMax * 0.9) / w

    On Error Resume Next
    ActiveSettings.TextStyle.Height = h
    ActiveSettings.TextStyle.Width = h * C_TILE_W
    ActiveSettings.TextStyle.Justification = msdTextJustificationCenterCenter
    Dim oT As TextElement
    Set oT = Nothing
    Set oT = CreateTextElement1(Nothing, s, Point3dFromXYZ(mx, my, 0#), Matrix3dIdentity)
    If Not oT Is Nothing Then oT.LineWeight = 0: ActiveModelReference.AddElement oT
    On Error GoTo 0
End Sub

' SUA 09/10/2026: dua chu bang toa do vao GIUA HANG: tim 2 duong ke NGANG
' gan nhat (tren/duoi) di qua cot x cua tag -> lay trung diem.
' Chi ap dung khi mau lay tu .dgn (mau .txt cu da tinh san tam hang).
Private Function TamHang(ByVal x As Double, ByVal y As Double) As Double
    TamHang = y
    If Not gTuDgn Then Exit Function
    Dim i As Long, j As Long, m As Long, co() As Double
    Dim ax As Double, ay As Double, bx As Double, by As Double, yy As Double
    Dim yt As Double, yd As Double
    yt = 1E+30: yd = -1E+30
    For i = 1 To gNL
        co = gLineCoords(i)
        m = (UBound(co) + 1) \ 2
        For j = 0 To m - 2
            ax = co(2 * j): ay = co(2 * j + 1): bx = co(2 * j + 2): by = co(2 * j + 3)
            If Abs(by - ay) <= 0.01 * Abs(bx - ax) And Abs(bx - ax) > 0.000001 Then
                If (x - ax) * (x - bx) <= 0# Then
                    yy = (ay + by) / 2#
                    If yy > y And yy < yt Then yt = yy
                    If yy <= y And yy > yd Then yd = yy
                End If
            End If
        Next j
    Next i
    If yt < 1E+29 And yd > -1E+29 Then
        If (yt - yd) < 100# Then TamHang = (yt + yd) / 2#
    End If
End Function

' Sap cell theo Y giam dan (tren xuong) - insertion sort song song
Private Sub SapGiamY(ByRef ax() As Double, ByRef ay() As Double, ByVal c As Long)
    Dim i As Long, j As Long, tX As Double, ty As Double
    For i = 2 To c
        tX = ax(i): ty = ay(i)
        j = i - 1
        Do While j >= 1
            If ay(j) < ty Then
                ax(j + 1) = ax(j): ay(j + 1) = ay(j): j = j - 1
            Else
                Exit Do
            End If
        Loop
        ax(j + 1) = tX: ay(j + 1) = ty
    Next i
End Sub

' Be rong (chieu=0) hoac cao (chieu=1) cua ring
Private Function found_bb(ByRef ring() As Double, ByVal chieu As Long) As Double
    Dim n As Long, i As Long, a As Double, b As Double
    n = UBound(ring, 1)
    a = ring(0, chieu): b = ring(0, chieu)
    For i = 1 To n - 1
        If ring(i, chieu) < a Then a = ring(i, chieu)
        If ring(i, chieu) > b Then b = ring(i, chieu)
    Next i
    found_bb = b - a
End Function


' Nguong x giu panel trai (bo panel phai neu mau co 2 panel canh nhau).
' Tra ve gXmax+1 neu chi 1 panel (giu het).
Private Function PanelTraiXlim() As Double
    Dim a As Double
    a = (gXmax - gXmin) * (gYmax - gYmin)
    Dim rminx() As Double, rmaxx() As Double, rarea() As Double, nR As Long
    ReDim rminx(1 To gNL + 1): ReDim rmaxx(1 To gNL + 1): ReDim rarea(1 To gNL + 1)
    nR = 0
    Dim i As Long, co() As Double, m As Long, j As Long
    Dim x1 As Double, x2 As Double, y1 As Double, y2 As Double
    For i = 1 To gNL
        co = gLineCoords(i)
        m = (UBound(co) + 1) \ 2
        If m = 4 Or m = 5 Then
            x1 = co(0): x2 = co(0): y1 = co(1): y2 = co(1)
            For j = 0 To m - 1
                If co(2 * j) < x1 Then x1 = co(2 * j)
                If co(2 * j) > x2 Then x2 = co(2 * j)
                If co(2 * j + 1) < y1 Then y1 = co(2 * j + 1)
                If co(2 * j + 1) > y2 Then y2 = co(2 * j + 1)
            Next j
            If (x2 - x1) * (y2 - y1) > 0.15 * a Then
                nR = nR + 1
                rminx(nR) = x1: rmaxx(nR) = x2: rarea(nR) = (x2 - x1) * (y2 - y1)
            End If
        End If
    Next i

    If nR < 2 Then PanelTraiXlim = gXmax + 1#: Exit Function

    ' Top-2 theo dien tich
    Dim i1 As Long, i2 As Long
    i1 = 1
    For i = 2 To nR
        If rarea(i) > rarea(i1) Then i1 = i
    Next i
    i2 = -1
    For i = 1 To nR
        If i <> i1 Then
            If i2 = -1 Then
                i2 = i
            ElseIf rarea(i) > rarea(i2) Then
                i2 = i
            End If
        End If
    Next i

    Dim lMax As Double, rMin As Double
    If rminx(i1) <= rminx(i2) Then
        lMax = rmaxx(i1): rMin = rminx(i2)
    Else
        lMax = rmaxx(i2): rMin = rminx(i1)
    End If

    If rMin > lMax - 1# Then
        PanelTraiXlim = lMax + (rMin - lMax) * 0.5
    Else
        PanelTraiXlim = gXmax + 1#
    End If
End Function


' Ve chu cho khung mau:
'  - Uu tien: dat NGUYEN chuoi, can le trai (LeftBottom) tai dung toa do mau.
'  - Neu that bai: lui ve cat doan <=48 ky tu, can giua theo be rong tinh tay.
Private Sub VeTextMau(ByVal x As Double, ByVal y As Double, _
                      ByVal s As String, ByVal hc As Double)
    If Len(s) = 0 Or hc <= 0 Then Exit Sub

    ' Thu 1: nguyen chuoi, can le trai
    If VeChuoiTrai(x, y, s, hc) Then Exit Sub

    ' Thu 2 (du phong): cat doan, can giua theo be rong tinh tay
    Dim startX As Double
    If gKieuCan = "G" Then
        startX = x - RongChuoi(s, hc) / 2#
    Else
        startX = x
    End If
    Const MAXLEN As Long = 48
    Dim p As Long, sub_s As String, w As Double, curX As Double
    curX = startX
    p = 1
    Do While p <= Len(s)
        sub_s = Mid$(s, p, MAXLEN)
        w = RongChuoi(sub_s, hc)
        On Error Resume Next
        ActiveSettings.TextStyle.Height = hc
        ActiveSettings.TextStyle.Width = hc * C_TILE_W
        ActiveSettings.TextStyle.Justification = msdTextJustificationCenterCenter
        Dim oT As TextElement
        Set oT = Nothing
        Set oT = CreateTextElement1(Nothing, sub_s, Point3dFromXYZ(curX + w / 2#, y, 0#), Matrix3dIdentity)
        If Not oT Is Nothing Then oT.LineWeight = 0: ActiveModelReference.AddElement oT
        On Error GoTo 0
        curX = curX + w
        p = p + MAXLEN
    Loop
End Sub

' Dat nguyen chuoi can le trai. Tra ve True neu thanh cong.
Private Function VeChuoiTrai(ByVal x As Double, ByVal y As Double, _
                             ByVal s As String, ByVal hc As Double) As Boolean
    VeChuoiTrai = False
    Dim px As Double
    If gKieuCan = "G" Then
        px = x - RongChuoi(s, hc) / 2#     ' che do giua: dich trai nua be rong
    Else
        px = x
    End If
    On Error Resume Next
    Err.Clear
    ActiveSettings.TextStyle.Height = hc
    ActiveSettings.TextStyle.Width = hc * C_TILE_W
    ActiveSettings.TextStyle.Justification = msdTextJustificationLeftBottom
    Dim oT As TextElement
    Set oT = Nothing
    Set oT = CreateTextElement1(Nothing, s, Point3dFromXYZ(px, y - hc * 0.5, 0#), Matrix3dIdentity)
    If (Not oT Is Nothing) And (Err.Number = 0) Then
        oT.LineWeight = 0
        ActiveModelReference.AddElement oT
        If Err.Number = 0 Then VeChuoiTrai = True
    End If
    On Error GoTo 0
End Function

' Uoc luong be rong chuoi theo tung ky tu (chinh xac hon cho dong nhieu dau cham)
Private Function RongChuoi(ByVal s As String, ByVal hc As Double) As Double
    Dim i As Long, c As String, w As Double
    For i = 1 To Len(s)
        c = Mid$(s, i, 1)
        Select Case c
            Case ".", ",", ";", ":", "'", "|", "!", "`"
                w = w + hc * 0.24
            Case " "
                w = w + hc * 0.26
            Case "i", "l", "I", "j", "t", "f", "r", "(", ")", "[", "]", "/", "-"
                w = w + hc * 0.32
            Case "m", "M", "W", "w"
                w = w + hc * 0.82
            Case Else
                w = w + hc * 0.5
        End Select
    Next i
    RongChuoi = w
End Function


'============================================================
' CHEN KHUNG PHU LUC 19 CHO 1 THUA CO SAN (goi tu dialog/CSDL)
'   found   : thua da co hinh hoc + thuoc tinh
'   mauPath : file mau ; kieuCan "T"/"G"
'============================================================
Public Sub ChenKhungTuThua(ByVal found As clsVung, ByVal mauPath As String, _
                           ByVal kieuCan As String, ByVal toBanDo As String, _
                           ByVal tenXa As String, ByVal tenHuyen As String, _
                           ByVal tenTinh As String, ByVal tyLe As Double)
    If found Is Nothing Then Exit Sub
    If Not found.HasRing Then MsgBox "Thua khong co hinh hoc.", vbExclamation: Exit Sub
    If Not NapMau(mauPath) Then
        MsgBox "Khong doc duoc file mau: " & mauPath, vbExclamation, "Trich luc": Exit Sub
    End If
    If UCase$(Trim$(kieuCan)) = "G" Then gKieuCan = "G" Else gKieuCan = "T"

    Dim cxb As Double, cyb As Double, bw As Double, bh As Double
    If Not TimBox(cxb, cyb, bw, bh) Then
        MsgBox "Khong tim thay o so do (level 24) trong mau.", vbExclamation, "Trich luc": Exit Sub
    End If

    ' Level ho so / level so do (form Trich luc, luu trong DiaChinhVL.ini)
    Dim lvCu As Level
    Set lvCu = ActiveSettings.Level
    ChuanBiLevel
    If Not gLvHSMot Is Nothing Then DatLv gLvHSMot

    Dim ring() As Double, n As Long, i As Long, j As Long
    ring = found.ring: n = UBound(ring, 1)
    Dim pw As Double, pH As Double
    pw = found_bb(ring, 0): pH = found_bb(ring, 1)

    ' ================= TY LE TO BAN DO =================
    ' SUA 05/08/2026: khung mau 19 phai CUNG CO GIAY du to ty le nao, nen k
    ' (ty le dat khung) phai TI LE THUAN voi ty le to:  k = tyLe / 20000.
    ' Kiem chung tu to 1:500 -> k=0.025 (cot X(m)=4.2203/168.8, chu=0.7/28).
    '   1:500  -> k=0.025    1:1000 -> k=0.05
    '   1:2000 -> k=0.10     1:5000 -> k=0.25
    ' Truoc day hardcode C_CANH_O=26.2 chi dung cho 1:500; to khac bi sai co.
    Dim mdDinh As Double
    mdDinh = gTyLeCu: If mdDinh <= 0 Then mdDinh = 500   ' mac dinh 500 lan dau
    If tyLe <= 0 Then tyLe = mdDinh          ' 0 = dung ty le lan truoc / mac dinh
    gTyLeCu = tyLe                           ' nho cho lan sau (form truyen xuong)

    Dim k As Double, kp As Double
    k = tyLe / 20000#                       ' ti le dat khung theo ty le to
    Dim bwm As Double, bhm As Double
    bwm = bw * k: bhm = bh * k

    ' SUA 05/08/2026: VE THUA THEO TY LE THAT + LAM TRON (giong gCadas
    ' TinhTyLe + DuTyLe). KHONG phong to nhet 82% nua.
    '   - kp = 1  -> thua ve dung ty le to ban do (nhu nhanh khong-template).
    '   - Neu thua LON hon o so do thi thu nho theo BUOC CHUAN (1/2, 1/2.5,
    '     1/5, 1/10...) = ty le so do van la boi so chuan cua ty le to.
    ' Kiem chung: thua 78 (13.4x12.7 m) vao o 24.7x26.2 m -> kp=1, chiem 54%,
    ' dung 1:500 nhu gCadas (truoc day ep 82% lam phong to 1.52 lan -> sai).
    Dim buoc As Variant, bi As Long
    buoc = Array(1#, 2#, 2.5, 5#, 10#, 20#, 25#, 50#, 100#)
    kp = 1#
    ' SUA 12/10/2026: ty le CHON TAY la ty le KHUNG; so do thua giu dung kich
    ' thuoc that (kp = 1) - thua lon tran o so do van ve dung. Chi thu nho khi
    ' ty le Tu dong ma thua qua lon (> 1:10000).
    If gTyLeTuDong Then
        For bi = 0 To UBound(buoc)
            kp = 1# / buoc(bi)
            If pw * kp <= bwm * 0.9 And pH * kp <= bhm * 0.9 Then Exit For
        Next bi
    End If
    If kp <= 0 Then kp = 1

    Dim Cpx As Double, Cpy As Double
    Cpx = found.cx: Cpy = found.cy
    ' SUA 09/10/2026: dat trich luc RA NGOAI ban do (ben phai pham vi ban ve) de
    ' o so do khong bi lan nhan/moc/chieu dai canh cua ban do (hoac lan xuat truoc).
    ' SUA 09/10/2026 (2): MAC DINH dat NGAY TAI THUA (theo yeu cau nguoi dung).
    ' Muon dat ra ngoai: DiaChinhVL.ini -> TL_DATNGOAI=1
    If DC_DocCauHinh("TL_DATNGOAI", "0") = "1" Then
        Dim rgM As Range3d, khoangTrai As Double
        On Error Resume Next
        rgM = ActiveModelReference.Range(True)
        If Err.Number = 0 And rgM.High.x > rgM.Low.x Then
            khoangTrai = (cxb - gXmin) * k              ' tu mep trai khung den tam o so do
            Cpx = rgM.High.x + (gXmax - gXmin) * k * 0.1 + khoangTrai
        End If
        Err.Clear
        On Error GoTo 0
    End If
    gTLCx = Cpx: gTLCy = Cpy

    ' Mau .dgn: chep nguyen phan tu (dung font/can le/vi tri nhu file mau)
    Dim chep As Boolean
    chep = (gTuDgn And gScDgn > 0 And Len(gDgnPath) > 0)
    If chep Then chep = (Len(Dir$(gDgnPath)) > 0)
    If chep Then
        DC_ChepMauDgn gDgnPath, gScDgn * k, Cpx - cxb * k, Cpy - cyb * k, found, _
                      toBanDo, tenXa, tenHuyen, tenTinh
    End If

    Dim slDT As Long, slTD As Long, slCD As Long
    slDT = 1: slTD = 2: slCD = 2
    Dim xlim As Double
    xlim = PanelTraiXlim()

    ' Lines cua khung (ti le co dinh k)
    Dim co() As Double, m As Long
    Dim ax As Double, ay As Double, bx As Double, by As Double, lminx As Double
    For i = 1 To gNL
        co = gLineCoords(i)
        m = (UBound(co) + 1) \ 2
        lminx = co(0)
        For j = 0 To m - 1
            If co(2 * j) < lminx Then lminx = co(2 * j)
        Next j
        If lminx >= xlim Then GoTo boLine2
        If chep Then GoTo boLine2                 ' da chep tu .dgn
        For j = 0 To m - 2
            ax = (co(2 * j) - cxb) * k + Cpx
            ay = (co(2 * j + 1) - cyb) * k + Cpy
            bx = (co(2 * j + 2) - cxb) * k + Cpx
            by = (co(2 * j + 3) - cyb) * k + Cpy
            If Abs(bx - ax) > 0.000001 Or Abs(by - ay) > 0.000001 Then VeLine ax, ay, bx, by, -1
        Next j
boLine2:
    Next i

    ReDim cellX_tt(1 To gNT) As Double: ReDim cellY_tt(1 To gNT) As Double: Dim c_tt As Long
    ReDim cellX_xx(1 To gNT) As Double: ReDim cellY_xx(1 To gNT) As Double: Dim c_xx As Long
    ReDim cellX_yy(1 To gNT) As Double: ReDim cellY_yy(1 To gNT) As Double: Dim c_yy As Long
    ReDim cellX_cd(1 To gNT) As Double: ReDim cellY_cd(1 To gNT) As Double: Dim c_cd As Long
    c_tt = 0: c_xx = 0: c_yy = 0: c_cd = 0
    Dim nTLThem As Long

    Dim s As String, gt As String, mx As Double, my As Double, hc As Double
    For i = 1 To gNT
        If gTX(i) >= xlim Then GoTo boTxt2
        mx = (gTX(i) - cxb) * k + Cpx
        my = (gTY(i) - cyb) * k + Cpy
        hc = gTCao(i) * k
        If hc <= 0 Then GoTo boTxt2
        s = gTS(i)
        If gTKind(i) = "TEXT" Then
            If Not chep Then VeTextMau mx, my, s, hc
        Else
            Select Case s
                ' SUA 15/10: mau .dgn co them bang tttl dai (trang bo sung) -> chi lay bang chinh
                Case "tttl", "tamXtl", "tamYtl", "cdtl"
                    If gCotDgn And (gTX(i) < CX_DINH - CW_DINH Or gTX(i) > CX_CANH + CW_CANH) Then
                        If s = "tttl" Then nTLThem = nTLThem + 1
                    ElseIf s = "tttl" Then
                        c_tt = c_tt + 1: cellX_tt(c_tt) = gTX(i): cellY_tt(c_tt) = TamHang(gTX(i), gTY(i))
                    ElseIf s = "tamXtl" Then
                        c_xx = c_xx + 1: cellX_xx(c_xx) = gTX(i): cellY_xx(c_xx) = TamHang(gTX(i), gTY(i))
                    ElseIf s = "tamYtl" Then
                        c_yy = c_yy + 1: cellX_yy(c_yy) = gTX(i): cellY_yy(c_yy) = TamHang(gTX(i), gTY(i))
                    Else
                        c_cd = c_cd + 1: cellX_cd(c_cd) = gTX(i): cellY_cd(c_cd) = TamHang(gTX(i), gTY(i))
                    End If
                Case Else
                    If Not chep Then
                        gt = GiaTriTag(s, found, toBanDo, tenXa, tenHuyen, tenTinh, slDT)
                        If Len(gt) > 0 Then VeTextMau mx, my, gt, hc
                    End If
            End Select
        End If
boTxt2:
    Next i

    Dim hcB As Double
    hcB = 28# * k
    DatLv mLvBang                     ' so lieu bang toa do
    SapGiamY cellX_tt, cellY_tt, c_tt
    SapGiamY cellX_xx, cellY_xx, c_xx
    SapGiamY cellX_yy, cellY_yy, c_yy
    SapGiamY cellX_cd, cellY_cd, c_cd

    ' Be rong kha dung cua tung cot, DO TU CHINH FILE MAU (khoang cach giua
    ' tag cot nay va tag cot ke tiep) -> thu nho chu cho vua o, khong tran.
    Dim wDinh As Double, wColX As Double, wColY As Double, wCanh As Double
    If c_tt >= 1 And c_yy >= 1 Then wDinh = Abs(cellX_yy(1) - cellX_tt(1))
    If c_yy >= 1 And c_xx >= 1 Then wColX = Abs(cellX_xx(1) - cellX_yy(1))
    If c_xx >= 1 And c_cd >= 1 Then wColY = Abs(cellX_cd(1) - cellX_xx(1))
    wCanh = wColY

    Dim dai As Double

    ' SUA 05/08/2026 (1): MOT co chu chung cho CA BANG.
    ' Truoc day moi o tu thu nho rieng -> so 10 chu so (cot X) bi thu nhieu
    ' hon so 9 chu so (cot Y) -> hai cot lech co chu nhau. Gio quet truoc
    ' toan bo o, lay co NHO NHAT, roi ve tat ca bang co do.
    ' SUA 11/10/2026: danh sach HANG cua bang = vong ngoai + cac vong dao (thua
    ' con nam lot trong). Moi vong: cac dinh, hang cuoi lap lai dinh dau (khep kin);
    ' so hieu dinh danh tiep nhau. rCanh(r) = chieu dai canh r -> r+1 (-1 = khong).
    Dim nR As Long, rSo() As String, rx() As Double, ry() As Double, rCanh() As Double
    TaoHangBang found, nR, rSo, rx, ry, rCanh

    Dim hB As Double
    hB = hcB
    Dim r As Long
    For r = 1 To nR
        If r <= c_tt Then
            hB = CaoVuaO(hB, rSo(r), hcB, CW_DINH * k)
            hB = CaoVuaO(hB, FNum(rx(r), slTD), hcB, CW_X * k)
            hB = CaoVuaO(hB, FNum(ry(r), slTD), hcB, CW_Y * k)
            If rCanh(r) >= 0# Then hB = CaoVuaO(hB, FNum(rCanh(r), slCD), hcB, CW_CANH * k)
        End If
    Next r

    ' SUA 11/10/2026: bang trang Trich luc chi co c_tt hang (mau tluc: 16).
    ' Hang 1..c_tt dien o day; hang c_tt+1 tro di (vd tu 17) dua sang bang
    ' trang "Trich luc ban do dia chinh" (ttkq/tamykq/tamxkq/cdkq), bang TRAI truoc.
    If nR > c_tt And c_tt > 0 Then
        ' SUA 16/10: bang noi tiep bat dau LAP LAI dinh cuoi (16) de co canh 16-17
        If Not DienBangKQ(c_tt, nR, rSo, rx, ry, rCanh, slTD, slCD, cxb, cyb, k, Cpx, Cpy) Then
            MsgBox "Thua co " & nR & " hang toa do, mau chi co " & c_tt & " hang (khong co bang ttkq).", vbExclamation, "Trich luc"
        End If
        If nTLThem > 0 Then DienBangKQ c_tt, nR, rSo, rx, ry, rCanh, slTD, slCD, cxb, cyb, k, Cpx, Cpy, False, "tl"
    End If
    If True Then
        DatLv mLvBang
        For r = 1 To nR
            If r <= c_tt Then
                ' Tat ca dat vao TAM cot (CX_*), hang y = cellY_tt(r) -> thang hang.
                DienCell CX_DINH, cellY_tt(r), rSo(r), hB, cxb, cyb, k, Cpx, Cpy, CW_DINH * k
                ' cot X(m) = toa do BAC ; cot Y(m) = toa do DONG
                DienCell CX_X, cellY_tt(r), FNum(rx(r), slTD), hB, cxb, cyb, k, Cpx, Cpy, CW_X * k
                DienCell CX_Y, cellY_tt(r), FNum(ry(r), slTD), hB, cxb, cyb, k, Cpx, Cpy, CW_Y * k
                ' canh r -> r+1 dat GIUA hai hang va GIUA cot canh
                If rCanh(r) >= 0# And (r + 1) <= c_tt Then _
                    DienCell CX_CANH, (cellY_tt(r) + cellY_tt(r + 1)) / 2#, FNum(rCanh(r), slCD), hB, cxb, cyb, k, Cpx, Cpy, CW_CANH * k
            End If
        Next r
    End If

    ' SUA 09/10/2026: bang phu o trang Ho so (tths/cdhs): so hieu dinh + chieu dai
    DienBangPhu "tths", "cdhs", nR, rSo, rCanh, cxb, cyb, k, Cpx, Cpy, rx, ry
    ' SUA 14/10/2026: bang ttkq NHO (vd trang "9. Toa do dinh thua") = ban sao bang
    ' tttl: dien tu hang 1 (truoc day chi dien bang ttkq dai cho hang 17+)
    DienBangKQ 1, nR, rSo, rx, ry, rCanh, slTD, slCD, cxb, cyb, k, Cpx, Cpy, True

    ' So do thua: THU NHO vua o (kp), tam o = tam khung (Cpx,Cpy)
    VeThuaTrongO found, Cpx, Cpy, kp, bwm * 0.03
    TK_VeThuaKe found, Cpx, Cpy, found.cx, found.cy, kp, bwm * 0.0252, Cpx, Cpy, bwm, bhm, toBanDo
    Set gLvHSMot = Nothing
    Set gLvHSMap = Nothing
    DatLv lvCu
End Sub

' Doc cau hinh level (LV_HS, LV_SD) -> level cho tung nhom phan tu.
'   Level ho so : 1 so  -> moi phan tu chep tu mau + so lieu bang ve level do
'                 nhieu -> giu level cua file mau (so lieu bang theo level tag bang)
'   Level so do : so thu 1 = canh thua, 2 = so hieu dinh, 3 = nhan thua
'                 (1 so -> ca so do ve 1 level)
Private Sub ChuanBiLevel()
    Dim dS() As Long, c As Long, i As Long
    Set mLvBang = Nothing: Set mLvRanh = Nothing
    Set mLvSo = Nothing: Set mLvNhan = Nothing
    Set gLvHSMot = Nothing
    Set gLvHSMap = Nothing
    If DC_DocCauHinh("LV_HS_ON", "1") = "1" Then
        c = DC_DsSoLevel(DC_DocCauHinh("LV_HS", DC_LV_HS_MD), dS)
        If c = 1 Then
            Set gLvHSMot = DC_LevelTheoSo(dS(0))
            Set mLvBang = gLvHSMot
        ElseIf c > 1 Then
            ' SUA 10/10/2026: NHIEU so -> moi phan tu ho so PHAI nam tren cac level
            ' da nhap (de "Luu file ho so" lay du). Cac level cua file mau (tang dan)
            ' lan luot ung voi cac so da nhap; mau nhieu level hon thi phan du ve so cuoi.
            ' Vd mau 24,56,60,61 + nhap 24,56,60,61 -> giu nguyen nhu mau.
            Dim lvMau() As Long, nm As Long, j As Long, k2 As Long, tmp As Long
            ReDim lvMau(1 To gNL + gNT + 1)
            For i = 1 To gNL
                ThemLvMau lvMau, nm, gLineLevel(i)
            Next i
            For i = 1 To gNT
                ThemLvMau lvMau, nm, gTL(i)
            Next i
            For i = 1 To nm - 1                 ' sap tang dan
                For j = i + 1 To nm
                    If lvMau(j) < lvMau(i) Then tmp = lvMau(i): lvMau(i) = lvMau(j): lvMau(j) = tmp
                Next j
            Next i
            Set gLvHSMap = CreateObject("Scripting.Dictionary")
            For i = 1 To nm
                k2 = i - 1: If k2 > c - 1 Then k2 = c - 1
                Set gLvHSMap(CStr(lvMau(i))) = DC_LevelTheoSo(dS(k2))
            Next i
            Set gLvHSMot = DC_LevelTheoSo(dS(c - 1))      ' level mau la -> so cuoi
            For i = 1 To gNT
                If gTS(i) = "tttl" Then
                    If gLvHSMap.Exists(CStr(gTL(i))) Then Set mLvBang = gLvHSMap(CStr(gTL(i)))
                    Exit For
                End If
            Next i
            If mLvBang Is Nothing Then Set mLvBang = gLvHSMot
        End If
    End If
    If DC_DocCauHinh("LV_SD_ON", "1") = "1" Then
        c = DC_DsSoLevel(DC_DocCauHinh("LV_SD", DC_LV_SD_MD), dS)
        If c >= 1 Then
            Set mLvRanh = DC_LevelTheoSo(dS(0))
            If c >= 2 Then Set mLvSo = DC_LevelTheoSo(dS(1)) Else Set mLvSo = mLvRanh
            If c >= 3 Then Set mLvNhan = DC_LevelTheoSo(dS(2)) Else Set mLvNhan = mLvSo
        End If
    End If
End Sub

' Bang phu (vd trang Phieu do dac / Ho so: "So hieu dinh thua | Chieu dai (m)").
' Chi dien 2 cot: so hieu dinh (tag tagTT, moi hang 1 dinh, hang cuoi lap dinh 1)
' va chieu dai canh (tag tagCD, canh thu i vao tag cd thu i). So hang theo thua.
Private Sub DienBangPhu(ByVal tagTT As String, ByVal tagCD As String, ByVal nR As Long, _
                        rSo() As String, rCanh() As Double, ByVal cxb As Double, ByVal cyb As Double, _
                        ByVal k As Double, ByVal Cpx As Double, ByVal Cpy As Double, _
                        rx() As Double, ry() As Double)
    Dim tX() As Double, ty() As Double, cx() As Double, cy() As Double
    Dim ct As Long, cc As Long, i As Long, hT As Double, hc As Double, lvT As Long
    ReDim tX(1 To gNT + 1): ReDim ty(1 To gNT + 1)
    ReDim cx(1 To gNT + 1): ReDim cy(1 To gNT + 1)
    For i = 1 To gNT
        If gTS(i) = tagTT Then
            ct = ct + 1: tX(ct) = gTX(i): ty(ct) = TamHang(gTX(i), gTY(i))
            hT = gTCao(i): lvT = gTL(i)
        ElseIf gTS(i) = tagCD Then
            cc = cc + 1: cx(cc) = gTX(i): cy(cc) = gTY(i): hc = gTCao(i)
        End If
    Next i
    If ct = 0 Then Exit Sub
    SapCotHang tX, ty, ct, hT * 2#
    If cc > 0 Then SapCotHang cx, cy, cc, hc * 2#
    DatLvTag lvT

    ' SUA 21/10: bang phu nhieu cot (vd 2 cot x 20 hang): sang cot moi LAP LAI dinh
    ' cuoi; canh r->r+1 dat o tag cd GIUA 2 o cung cot. rw(i) = hang du lieu cua o i.
    Dim w As Double, xc As Double, xT As Double, r As Long, rw() As Long, yc As Double
    ReDim rw(1 To ct + 1): r = 1
    If hc <= 0 Then hc = hT
    For i = 1 To ct
        If r > nR Then Exit For
        rw(i) = r
        xc = TamCot(tX(i), ty(i), w)
        DienCell xc, ty(i), rSo(r), hT * k, cxb, cyb, k, Cpx, Cpy, w * k
        If rCanh(r) >= 0# And r < nR And i < ct Then
            If Abs(tX(i + 1) - tX(i)) < hT * 2# Then
                yc = (ty(i) + ty(i + 1)) / 2#
                xT = TagCanhPhai(tagCD, tX(i), yc, hT * 2#)
                If xT > -1E+29 Then xc = TamCot(xT, yc, w): DienCell xc, yc, FNum(rCanh(r), 2), hc * k, cxb, cyb, k, Cpx, Cpy, w * k
            Else
                r = r - 1
            End If
        End If
        r = r + 1
    Next i
    ' SUA 14/10/2026: bang phu co cot toa do (tag tamxhs = X Bac, tamyhs = Y Dong)
    ' -> dien theo hang cua tag tths (chi lay tag cung hang, bo tag rac o cho khac)
    Dim m As Long, best As Long, dBest As Double, dd As Double, tg As Variant, gTri As Double
    For Each tg In Array("tamxhs", "tamyhs")
        For i = 1 To ct
            If rw(i) = 0 Then Exit For
            best = 0: dBest = hT * 0.8
            For m = 1 To gNT
                If gTS(m) = tg Then
                    dd = Abs(TamHang(gTX(m), gTY(m)) - ty(i))
                    If dd < dBest And gTX(m) > tX(i) Then dBest = dd: best = m
                End If
            Next m
            If best > 0 Then
                If tg = "tamxhs" Then gTri = rx(rw(i)) Else gTri = ry(rw(i))
                xc = TamCot(gTX(best), gTY(best), w)
                DienCell xc, ty(i), FNum(gTri, 2), gTCao(best) * k, cxb, cyb, k, Cpx, Cpy, w * k
            End If
        Next i
    Next tg
End Sub

' Danh sach hang bang toa do: vong ngoai + cac vong dao
Private Sub TaoHangBang(ByVal v As clsVung, ByRef nR As Long, ByRef rSo() As String, _
                        ByRef rx() As Double, ByRef ry() As Double, ByRef rCanh() As Double)
    Dim vong As New Collection, rg() As Double, kv As Long, m As Long, i As Long, so As Long
    vong.Add v.ring
    For kv = 1 To v.dao.Count
        vong.Add v.dao.Item(kv)
    Next kv
    nR = 0
    For kv = 1 To vong.Count
        rg = vong.Item(kv): nR = nR + UBound(rg, 1) + 1
    Next kv
    ReDim rSo(1 To nR + 1): ReDim rx(1 To nR + 1): ReDim ry(1 To nR + 1): ReDim rCanh(1 To nR + 1)
    nR = 0: so = 0
    For kv = 1 To vong.Count
        rg = vong.Item(kv): m = UBound(rg, 1)        ' rg(m) = rg(0) (vong kin)
        For i = 0 To m - 1
            nR = nR + 1
            rSo(nR) = CStr(so + i + 1)
            rx(nR) = rg(i, 1): ry(nR) = rg(i, 0)      ' X = toa do BAC, Y = DONG
            rCanh(nR) = Sqr((rg(i + 1, 0) - rg(i, 0)) ^ 2 + (rg(i + 1, 1) - rg(i, 1)) ^ 2)
        Next i
        nR = nR + 1                                    ' hang khep vong
        rSo(nR) = CStr(so + 1): rx(nR) = rg(0, 1): ry(nR) = rg(0, 0): rCanh(nR) = -1#
        so = so + m
    Next kv
End Sub

' Bang tren trang "TRICH LUC BAN DO DIA CHINH" (ttkq / tamykq / tamxkq / cdkq).
' Hang sap theo cot (bang trai truoc, roi bang phai), trong moi bang tu tren xuong.
' Tra ve False neu mau khong co bang nay.
Private Function DienBangKQ(ByVal r0 As Long, ByVal nR As Long, rSo() As String, rx() As Double, ry() As Double, _
                            rCanh() As Double, ByVal slTD As Long, ByVal slCD As Long, _
                            ByVal cxb As Double, ByVal cyb As Double, ByVal k As Double, _
                            ByVal Cpx As Double, ByVal Cpy As Double, _
                            Optional ByVal bangNho As Boolean = False, Optional ByVal hau As String = "kq") As Boolean
    Dim tX() As Double, ty() As Double, ct As Long, i As Long, hT As Double, lvT As Long
    ReDim tX(1 To gNT + 1): ReDim ty(1 To gNT + 1)
    For i = 1 To gNT
        If gTS(i) = "tt" & hau Then
            ct = ct + 1: tX(ct) = gTX(i): ty(ct) = TamHang(gTX(i), gTY(i))
            hT = gTCao(i): lvT = gTL(i)
        End If
    Next i
    If ct = 0 Then Exit Function
    ' Mau co the co nhieu bang ttkq: bang nho (16 hang) tren trang co so do va
    ' 2 bang DAI dat canh nhau. Chi lay cac cot co nhieu hang nhat (bang dai).
    Dim i2 As Long, dem As Long, demMax As Long, nCot() As Long
    ReDim nCot(1 To ct)
    For i = 1 To ct
        dem = 0
        For i2 = 1 To ct
            If Abs(tX(i2) - tX(i)) < hT * 2# Then dem = dem + 1
        Next i2
        nCot(i) = dem
        If dem > demMax Then demMax = dem
    Next i
    dem = 0
    For i = 1 To ct
        If (nCot(i) * 2 > demMax) Xor bangNho Then dem = dem + 1: tX(dem) = tX(i): ty(dem) = ty(i)
    Next i
    ct = dem
    If ct = 0 Then Exit Function
    SapCotHang tX, ty, ct, hT * 2#
    DatLvTag lvT

    Dim w As Double, xc As Double, xT As Double, r As Long, hc As Double, sL As Long
    hc = hT * k
    ' sl = o (slot) trong bang, r = hang du lieu (bat dau tu r0, vd 17)
    r = r0: sL = 0
    Do While r <= nR And sL < ct
        sL = sL + 1
        xc = TamCot(tX(sL), ty(sL), w)
        DienCell xc, ty(sL), rSo(r), hc, cxb, cyb, k, Cpx, Cpy, w * k
        xT = TagCanhPhai("tamy" & hau, tX(sL), ty(sL), hT)
        If xT > -1E+29 Then xc = TamCot(xT, ty(sL), w): DienCell xc, ty(sL), FNum(rx(r), slTD), hc, cxb, cyb, k, Cpx, Cpy, w * k
        xT = TagCanhPhai("tamx" & hau, tX(sL), ty(sL), hT)
        If xT > -1E+29 Then xc = TamCot(xT, ty(sL), w): DienCell xc, ty(sL), FNum(ry(r), slTD), hc, cxb, cyb, k, Cpx, Cpy, w * k
        ' canh r -> r+1: giua 2 o, chi khi o ke tiep cung 1 bang (cung cot)
        If rCanh(r) >= 0# And r < nR And sL + 1 <= ct Then
            If Abs(tX(sL + 1) - tX(sL)) < hT * 2# Then
                xT = TagCanhPhai("cd" & hau, tX(sL), (ty(sL) + ty(sL + 1)) / 2#, hT * 2#)
                If xT > -1E+29 Then
                    xc = TamCot(xT, ty(sL), w)
                    DienCell xc, (ty(sL) + ty(sL + 1)) / 2#, FNum(rCanh(r), slCD), hc, cxb, cyb, k, Cpx, Cpy, w * k
                End If
            End If
        End If
        ' SUA 16/10: sang cot/bang moi -> lap lai dinh vua ghi (co canh noi tiep)
        If sL + 1 <= ct And r < nR Then
            If Abs(tX(sL + 1) - tX(sL)) >= hT * 2# Then r = r - 1
        End If
        r = r + 1
    Loop
    If r <= nR And Not bangNho Then MsgBox "Thua co " & nR & " hang toa do, bang khong du cho (con " & (nR - r + 1) & " hang).", vbExclamation, "Trich luc"
    DienBangKQ = True
End Function

' X cua tag (ten) gan nhat ben PHAI x0, cung hang (|dy| <= dyMax). Khong co -> -1E+30
Private Function TagCanhPhai(ByVal ten As String, ByVal X0 As Double, ByVal Y0 As Double, _
                             ByVal dyMax As Double) As Double
    Dim i As Long, best As Double, yy As Double
    TagCanhPhai = -1E+30: best = 1E+30
    If dyMax <= 0 Then dyMax = 1#
    For i = 1 To gNT
        If StrComp(gTS(i), ten, vbTextCompare) = 0 Then
            If gTX(i) > X0 Then
                yy = TamHang(gTX(i), gTY(i))
                If Abs(yy - Y0) <= dyMax * 1.5 Or Abs(gTY(i) - Y0) <= dyMax * 1.5 Then
                    If gTX(i) - X0 < best Then best = gTX(i) - X0: TagCanhPhai = gTX(i)
                End If
            End If
        End If
    Next i
End Function

' Dat level cho so lieu bang theo level cua tag trong mau
Private Sub DatLvTag(ByVal lvT As Long)
    If Not gLvHSMap Is Nothing Then
        If gLvHSMap.Exists(CStr(lvT)) Then DatLv gLvHSMap(CStr(lvT)) Else DatLv gLvHSMot
    ElseIf Not gLvHSMot Is Nothing Then
        DatLv gLvHSMot
    ElseIf lvT > 0 And DC_DocCauHinh("LV_HS_ON", "1") = "1" Then
        DatLv DC_LevelTheoSo(lvT)
    End If
End Sub

' Sap tag bang: theo COT (trai -> phai, sai so tol), trong cot tu tren xuong

' Sap tag bang: theo COT (trai -> phai, sai so tol), trong cot tu tren xuong
Private Sub SapCotHang(ByRef ax() As Double, ByRef ay() As Double, ByVal c As Long, ByVal tol As Double)
    Dim i As Long, j As Long, x As Double, y As Double, truoc As Boolean
    If tol <= 0 Then tol = 1#
    For i = 2 To c
        x = ax(i): y = ay(i): j = i - 1
        Do While j >= 1
            If Abs(ax(j) - x) > tol Then
                truoc = (ax(j) > x)
            Else
                truoc = (ay(j) < y)
            End If
            If Not truoc Then Exit Do
            ax(j + 1) = ax(j): ay(j + 1) = ay(j): j = j - 1
        Loop
        ax(j + 1) = x: ay(j + 1) = y
    Next i
End Sub

' Tam cot: 2 duong ke DOC gan nhat (trai/phai) cat qua hang y. w = be rong cot.
Private Function TamCot(ByVal x As Double, ByVal y As Double, ByRef w As Double) As Double
    Dim i As Long, j As Long, m As Long, co() As Double
    Dim ax As Double, ay As Double, bx As Double, by As Double, xx As Double
    Dim xl As Double, xr As Double
    TamCot = x: w = 0#
    xl = -1E+30: xr = 1E+30
    For i = 1 To gNL
        co = gLineCoords(i)
        m = (UBound(co) + 1) \ 2
        For j = 0 To m - 2
            ax = co(2 * j): ay = co(2 * j + 1): bx = co(2 * j + 2): by = co(2 * j + 3)
            If Abs(bx - ax) <= 0.01 * Abs(by - ay) And Abs(by - ay) > 0.000001 Then
                If (y - ay) * (y - by) <= 0# Then
                    xx = (ax + bx) / 2#
                    If xx <= x And xx > xl Then xl = xx
                    If xx > x And xx < xr Then xr = xx
                End If
            End If
        Next j
    Next i
    If xl > -1E+29 And xr < 1E+29 Then
        If (xr - xl) < 1000# Then TamCot = (xl + xr) / 2#: w = xr - xl
    End If
End Function

Private Sub ThemLvMau(ByRef a() As Long, ByRef n As Long, ByVal lv As Long)
    Dim i As Long
    If lv <= 0 Then Exit Sub
    For i = 1 To n
        If a(i) = lv Then Exit Sub
    Next i
    n = n + 1: a(n) = lv
End Sub

Private Sub DatLv(ByVal lv As Level)
    If lv Is Nothing Then Exit Sub
    On Error Resume Next
    Set ActiveSettings.Level = lv
    Err.Clear
End Sub

' Ve so do thua da THU NHO (kp) vao o so do, tam o tai (cx,cy)
Private Sub VeThuaTrongO(ByVal v As clsVung, ByVal cx As Double, ByVal cy As Double, _
                         ByVal kp As Double, ByVal cao As Double)
    Dim ring() As Double, n As Long, i As Long
    ring = v.ring: n = UBound(ring, 1)
    If n < 3 Then Exit Sub
    If cao <= 0 Then cao = 0.5
    Dim rMoc As Double: rMoc = cao * 0.5
    Dim ax As Double, ay As Double, bx As Double, by As Double
    Dim mx As Double, my As Double, dai As Double
    Dim k2 As Long, dr() As Double, m As Long

    DatLv mLvRanh                     ' canh thua
    For i = 0 To n - 1
        ax = cx + (ring(i, 0) - v.cx) * kp: ay = cy + (ring(i, 1) - v.cy) * kp
        bx = cx + (ring(i + 1, 0) - v.cx) * kp: by = cy + (ring(i + 1, 1) - v.cy) * kp
        VeLine ax, ay, bx, by, -1
    Next i
    For k2 = 1 To v.dao.Count
        dr = v.dao.Item(k2): m = UBound(dr, 1)
        For i = 0 To m - 1
            ax = cx + (dr(i, 0) - v.cx) * kp: ay = cy + (dr(i, 1) - v.cy) * kp
            bx = cx + (dr(i + 1, 0) - v.cx) * kp: by = cy + (dr(i + 1, 1) - v.cy) * kp
            VeLine ax, ay, bx, by, -1
        Next i
    Next k2
    ' SUA 09/10/2026 (theo yeu cau): BO o vuong moc dinh va chieu dai canh trong
    ' so do (chieu dai da co trong bang toa do). Chi giu SO HIEU DINH + nhan thua.
    DatLv mLvSo                       ' so hieu dinh
    ' SUA 12/10/2026: so hieu dinh = 80% co chu nhan thua (nhan = cao * 0.84)
    Dim caoS As Double: caoS = cao * 0.84 * 0.8
    ' SUA 15/10/2026: so hieu dinh dat RA NGOAI thua theo phan giac goc
    Dim hx As Double, hy As Double, kc As Double
    For i = 0 To n - 1
        ax = cx + (ring(i, 0) - v.cx) * kp: ay = cy + (ring(i, 1) - v.cy) * kp
        HuongNgoai ring, n, i, False, hx, hy
        kc = caoS * (0.75 + 0.3 * Len(CStr(i + 1)))
        VeText ax + hx * kc, ay + hy * kc, CStr(i + 1), caoS, -1
    Next i
    ' SUA 11/10/2026: so hieu dinh cac vong dao (thua con lot trong) - danh tiep
    Dim soTiep As Long: soTiep = n
    For k2 = 1 To v.dao.Count
        dr = v.dao.Item(k2): m = UBound(dr, 1)
        For i = 0 To m - 1
            ax = cx + (dr(i, 0) - v.cx) * kp: ay = cy + (dr(i, 1) - v.cy) * kp
            HuongNgoai dr, m, i, True, hx, hy
            kc = caoS * (0.75 + 0.3 * Len(CStr(soTiep + i + 1)))
            VeText ax + hx * kc, ay + hy * kc, CStr(soTiep + i + 1), caoS, -1
        Next i
        soTiep = soTiep + m
    Next k2

    ' SUA 05/08/2026: NHAN GIUA THUA (giong gCadas):  LoaiDat  SoThua/DienTich
    '   vd:  CLN 78/84,2   (dien tich tu dong = v.Dt, lam tron 1 so le)
    ' Co chu = cao * 0.84 -> dung 0.625 m nhu gCadas o 1:500. Vi 'cao' bat nguon
    ' tu bwm (khung * tyLe/20000) nen nhan TU DONG co theo ty le to, tren giay
    ' luon ~1.25 mm du to 500/1000/2000/5000.
    DatLv mLvNhan                     ' nhan thua
    Dim caoN As Double: caoN = cao * 0.84
    Dim sLoai As String, sSo As String, sDt As String
    sLoai = Trim$(v.loaiDat): sSo = Trim$(v.soThua): sDt = FNum(v.dt, 1)
    Dim wLoai As Double, wFrac As Double, gap As Double, tong As Double, lefX As Double
    wLoai = Len(sLoai) * caoN * 0.6
    wFrac = Len(sDt) * caoN * 0.6
    If Len(sSo) * caoN * 0.6 > wFrac Then wFrac = Len(sSo) * caoN * 0.6
    gap = caoN * 0.4
    tong = wLoai + gap + wFrac
    lefX = cx - tong / 2#
    If Len(sLoai) > 0 Then VeText lefX + wLoai / 2#, cy, sLoai, caoN, -1
    VeNhanPhanSo lefX + wLoai + gap + wFrac / 2#, cy, sSo, sDt, caoN, -1
End Sub


'============================================================
' Cot bang muc 8 (tam X va be rong o, toa do MAU)
'============================================================
' Huong don vi tu dinh i ra NGOAI thua (vong dao: vao trong lo)
Private Sub HuongNgoai(r() As Double, ByVal n As Long, ByVal i As Long, ByVal dao As Boolean, dx As Double, dy As Double)
    Dim p As Long, q As Long, ux As Double, uy As Double, wx As Double, wy As Double, L As Double, e As Double
    p = i - 1: If p < 0 Then p = n - 1
    q = i + 1
    ux = r(i, 0) - r(p, 0): uy = r(i, 1) - r(p, 1): L = Sqr(ux * ux + uy * uy): If L > 0 Then ux = ux / L: uy = uy / L
    wx = r(i, 0) - r(q, 0): wy = r(i, 1) - r(q, 1): e = Sqr(wx * wx + wy * wy): If e > 0 Then wx = wx / e: wy = wy / e
    If e > L Then e = L
    dx = ux + wx: dy = uy + wy: L = Sqr(dx * dx + dy * dy)
    If L < 0.2 Then dx = -uy: dy = ux: L = 1
    dx = dx / L: dy = dy / L
    e = e * 0.05
    If DiemTrongPolygon(r, r(i, 0) + dx * e, r(i, 1) + dy * e) Xor dao Then dx = -dx: dy = -dy
End Sub

Private Sub DatCotMacDinh()
    CX_DINH = 117720.35: CX_X = 117842.1: CX_Y = 118014.25: CX_CANH = 118237.4
    CW_DINH = 74.7: CW_X = 168.8: CW_Y = 175.5: CW_CANH = 270.8
End Sub

' Mau tu .dgn: moi loai tag (tttl, tamYtl, tamXtl, cdtl) nam trong 1 cot;
' cot = khoang giua 2 duong ke DOC gan nhat (trai/phai) cua bang.
' (tamYtl nam o cot X(m), tamXtl o cot Y(m) - giong quy uoc mau cu)
' Kiem chung: mau cu tinh ra dung 8 so trong DatCotMacDinh.
Private Sub TinhCotTuLuoi()
    Dim xT(0 To 3) As Double, t As Long, i As Long, j As Long
    Dim y1 As Double, y2 As Double, coY As Boolean
    For t = 0 To 3: xT(t) = 1E+30: Next t
    For i = 1 To gNT
        t = -1
        Select Case gTS(i)
            Case "tttl": t = 0
            Case "tamYtl": t = 1
            Case "tamXtl": t = 2
            Case "cdtl": t = 3
        End Select
        If t >= 0 Then
            If gTX(i) < xT(t) Then xT(t) = gTX(i)
        End If
    Next i
    If xT(0) > 1E+29 Then Exit Sub
    For i = 1 To gNT
        If gTS(i) = "tttl" And Abs(gTX(i) - xT(0)) < 5# Then
            If Not coY Then
                y1 = gTY(i): y2 = gTY(i): coY = True
            Else
                If gTY(i) < y1 Then y1 = gTY(i)
                If gTY(i) > y2 Then y2 = gTY(i)
            End If
        End If
    Next i
    If Not coY Or y2 - y1 <= 0# Then Exit Sub

    ' Duong ke doc cat qua it nhat nua khoang cac hang cua bang
    Dim vx() As Double, nV As Long, c() As Double, m As Long
    Dim lo As Double, hi As Double, tg As Double
    ReDim vx(1 To 2000)
    For i = 1 To gNL
        c = gLineCoords(i): m = (UBound(c) + 1) \ 2
        For j = 0 To m - 2
            If Abs(c(2 * j) - c(2 * j + 2)) < 0.5 Then
                lo = c(2 * j + 1): hi = c(2 * j + 3)
                If lo > hi Then tg = lo: lo = hi: hi = tg
                If lo < y1 Then lo = y1
                If hi > y2 Then hi = y2
                If hi - lo > 0.5 * (y2 - y1) And nV < 2000 Then
                    nV = nV + 1: vx(nV) = c(2 * j)
                End If
            End If
        Next j
    Next i
    If nV < 2 Then Exit Sub

    Dim xl As Double, xr As Double
    For t = 0 To 3
        If xT(t) < 1E+29 Then
            xl = -1E+30: xr = 1E+30
            For j = 1 To nV
                If vx(j) <= xT(t) + 1# And vx(j) > xl Then xl = vx(j)
                If vx(j) > xT(t) + 1# And vx(j) < xr Then xr = vx(j)
            Next j
            If xl > -1E+29 And xr < 1E+29 Then
                Select Case t
                    Case 0: CX_DINH = (xl + xr) / 2#: CW_DINH = xr - xl: gCotDgn = True
                    Case 1: CX_X = (xl + xr) / 2#: CW_X = xr - xl
                    Case 2: CX_Y = (xl + xr) / 2#: CW_Y = xr - xl
                    Case 3: CX_CANH = (xl + xr) / 2#: CW_CANH = xr - xl
                End Select
            End If
        End If
    Next t
End Sub

'============================================================
' BAN VE TACH / HOP THUA (Mau 22/DK - 22tach.dgn / 22hop.dgn)
'   O so do TRUOC = level 25, o so do SAU = level 24 (dat ngay tai thua).
'   Bang "Doan | Chieu dai" = chu mau "tt" / "cd" (trang 2 roi trang 3).
'============================================================
Public Sub ChenKhungTachHop(ByVal cheDo As Long, ByVal goc As Collection, ByVal sau As Collection, _
                            ByVal vChinh As clsVung, ByVal mauPath As String, ByVal toBanDo As String, _
                            ByVal tenXa As String, ByVal tenHuyen As String, ByVal tenTinh As String, _
                            ByVal tyLe As Double)
    If Not NapMau(mauPath) Then
        MsgBox "Khong doc duoc file mau: " & mauPath, vbExclamation, "Tach/hop thua": Exit Sub
    End If
    Dim cxb As Double, cyb As Double, bw As Double, bh As Double
    If Not TimBox(cxb, cyb, bw, bh) Then
        MsgBox "Khong tim thay o so do SAU (level 24) trong mau.", vbExclamation, "Tach/hop thua": Exit Sub
    End If
    Dim cxt As Double, cyt As Double, bwt As Double, bht As Double
    If Not TimBoxLv(25, cxb, cyb, cxt, cyt, bwt, bht) Then
        cxt = cxb: cyt = cyb: bwt = bw: bht = bh       ' khong co o truoc -> ve chung o
    End If

    Dim lvCu As Level
    Set lvCu = ActiveSettings.Level
    ChuanBiLevel
    If Not gLvHSMot Is Nothing Then DatLv gLvHSMot

    ' Ty le khung + ty le so do (giong trich luc)
    If tyLe <= 0 Then tyLe = 500
    Dim k As Double, kp As Double, bwm As Double, bhm As Double
    k = tyLe / 20000#
    bwm = bw * k: bhm = bh * k
    Dim rg() As Double, x1 As Double, y1 As Double, x2 As Double, y2 As Double
    rg = vChinh.ring
    BaoRing rg, x1, y1, x2, y2
    Dim pw As Double, pH As Double, wMin As Double, hMin As Double
    pw = x2 - x1: pH = y2 - y1
    wMin = bw: If bwt < wMin Then wMin = bwt
    hMin = bh: If bht < hMin Then hMin = bht
    Dim buoc As Variant, bi As Long
    buoc = Array(1#, 2#, 2.5, 5#, 10#, 20#, 25#, 50#, 100#)
    kp = 1#
    If gTyLeTuDong Then
        For bi = 0 To UBound(buoc)
            kp = 1# / buoc(bi)
            If pw * kp <= wMin * k * 0.85 And pH * kp <= hMin * k * 0.85 Then Exit For
        Next bi
    End If
    Dim gx As Double, gy As Double               ' tam khung bao thua chinh
    gx = (x1 + x2) / 2#: gy = (y1 + y2) / 2#

    ' Dat o so do SAU ngay tai thua
    Dim Cpx As Double, Cpy As Double
    Cpx = gx: Cpy = gy
    gTLCx = Cpx: gTLCy = Cpy

    ' 1) Chep mau .dgn (modMauDgn thay chu mau qua modTachHop.TH_ThayChu)
    Dim chep As Boolean
    chep = (gTuDgn And gScDgn > 0 And Len(gDgnPath) > 0)
    If chep Then chep = (Len(Dir$(gDgnPath)) > 0)
    If chep Then
        DC_ChepMauDgn gDgnPath, gScDgn * k, Cpx - cxb * k, Cpy - cyb * k, goc.Item(1), _
                      toBanDo, tenXa, tenHuyen, tenTinh
    Else
        VeKhungTuCache cxb, cyb, k, Cpx, Cpy
    End If

    ' 2) So do TRUOC (o level 25) va SAU (o level 24)
    Dim cao As Double
    cao = bwm * 0.03
    Dim tX As Double, ty As Double
    tX = Cpx + (cxt - cxb) * k: ty = Cpy + (cyt - cyb) * k
    VeSoDoTH goc, tX, ty, gx, gy, kp, cao, False
    VeSoDoTH sau, Cpx, Cpy, gx, gy, kp, cao, True
    If cheDo = 2 Then TH_VeRanhChung Cpx, Cpy, gx, gy, kp   ' SUA 22/10
    TK_VeThuaKe vChinh, tX, ty, gx, gy, kp, cao * 0.84, tX, ty, bwt * k, bht * k, toBanDo
    TK_VeThuaKe vChinh, Cpx, Cpy, gx, gy, kp, cao * 0.84, Cpx, Cpy, bw * k, bh * k, toBanDo

    ' 3) Bang Doan / Chieu dai
    DienBangDoan sau, cxb, cyb, k, Cpx, Cpy
    Dim pS() As String, pC() As Double, px() As Double, py() As Double, pN As Long  ' SUA 28/10 bang phu
    pN = TH_BangPhu(pS, pC, px, py)
    If pN > 0 Then DienBangPhu "tths", "cdhs", pN, pS, pC, cxb, cyb, k, Cpx, Cpy, px, py

    Set gLvHSMot = Nothing
    Set gLvHSMap = Nothing
    DatLv lvCu
End Sub

' Ty le tu dong cho tach/hop: ty le chuan nho nhat de thua chinh (pw x ph)
' nam vua CA 2 o so do (truoc/sau) o ty le that -> so do sau trung khit ban do.
Public Function DC_TyLeTachHop(ByVal mauPath As String, ByVal pw As Double, ByVal pH As Double) As Double
    Dim cxb As Double, cyb As Double, bw As Double, bh As Double
    Dim cxt As Double, cyt As Double, bwt As Double, bht As Double
    Dim dS As Variant, i As Long
    DC_TyLeTachHop = 500
    If Not NapMau(mauPath) Then Exit Function
    If Not TimBox(cxb, cyb, bw, bh) Then Exit Function
    If TimBoxLv(25, cxb, cyb, cxt, cyt, bwt, bht) Then
        If bwt < bw Then bw = bwt
        If bht < bh Then bh = bht
    End If
    dS = Array(200#, 500#, 700#, 1000#, 2000#, 5000#, 10000#)
    For i = 0 To UBound(dS)
        If pw <= bw * dS(i) / 20000# * 0.85 And pH <= bh * dS(i) / 20000# * 0.85 Then
            DC_TyLeTachHop = dS(i): Exit Function
        End If
    Next i
    DC_TyLeTachHop = 10000#
End Function

' O so do tren level lv (lon nhat, khac o (cxb,cyb))
Private Function TimBoxLv(ByVal lv As Long, ByVal cxb As Double, ByVal cyb As Double, _
                          ByRef cx As Double, ByRef cy As Double, _
                          ByRef bw As Double, ByRef bh As Double) As Boolean
    Dim i As Long, j As Long, co() As Double, m As Long, bestA As Double
    Dim x1 As Double, y1 As Double, x2 As Double, y2 As Double
    bestA = -1
    For i = 1 To gNL
        If gLineLevel(i) = lv Then
            co = gLineCoords(i)
            m = (UBound(co) + 1) \ 2
            If m >= 4 Then
                x1 = co(0): x2 = co(0): y1 = co(1): y2 = co(1)
                For j = 0 To m - 1
                    If co(2 * j) < x1 Then x1 = co(2 * j)
                    If co(2 * j) > x2 Then x2 = co(2 * j)
                    If co(2 * j + 1) < y1 Then y1 = co(2 * j + 1)
                    If co(2 * j + 1) > y2 Then y2 = co(2 * j + 1)
                Next j
                If (x2 - x1) * (y2 - y1) > bestA Then
                    bestA = (x2 - x1) * (y2 - y1)
                    cx = (x1 + x2) / 2#: cy = (y1 + y2) / 2#: bw = x2 - x1: bh = y2 - y1
                End If
            End If
        End If
    Next i
    TimBoxLv = (bestA > 0)
End Function

' Mau .txt (khong chep duoc .dgn): ve duong + chu tu cache
Private Sub VeKhungTuCache(ByVal cxb As Double, ByVal cyb As Double, ByVal k As Double, _
                           ByVal Cpx As Double, ByVal Cpy As Double)
    Dim i As Long, j As Long, co() As Double, m As Long
    Dim ax As Double, ay As Double, bx As Double, by As Double
    For i = 1 To gNL
        co = gLineCoords(i)
        m = (UBound(co) + 1) \ 2
        For j = 0 To m - 2
            ax = (co(2 * j) - cxb) * k + Cpx: ay = (co(2 * j + 1) - cyb) * k + Cpy
            bx = (co(2 * j + 2) - cxb) * k + Cpx: by = (co(2 * j + 3) - cyb) * k + Cpy
            If Abs(bx - ax) > 0.000001 Or Abs(by - ay) > 0.000001 Then VeLine ax, ay, bx, by, -1
        Next j
    Next i
    For i = 1 To gNT
        If gTKind(i) = "TEXT" And gTCao(i) > 0 Then
            VeTextMau (gTX(i) - cxb) * k + Cpx, (gTY(i) - cyb) * k + Cpy, gTS(i), gTCao(i) * k
        End If
    Next i
End Sub

' Ve 1 so do: canh cac thua (canh chung ve 1 lan), so hieu dinh, nhan thua,
' (coKichThuoc) chieu dai canh doc theo canh.
'   Diem P (ban do) -> (ox, oy) + (P - (gx, gy)) * kp
Private Sub VeSoDoTH(ByVal dS As Collection, ByVal ox As Double, ByVal oy As Double, _
                     ByVal gx As Double, ByVal gy As Double, ByVal kp As Double, _
                     ByVal cao As Double, ByVal coKichThuoc As Boolean)
    Dim daVe As Object, daSo As Object
    Set daVe = CreateObject("Scripting.Dictionary")
    Set daSo = CreateObject("Scripting.Dictionary")
    Dim j As Long, kv As Long, i As Long, m As Long, v As clsVung, rg() As Double
    Dim ax As Double, ay As Double, bx As Double, by As Double, key As String, s As String
    Dim rMoc As Double: rMoc = cao * 0.5
    Dim hx As Double, hy As Double, kc As Double

    For j = 1 To dS.Count
        Set v = dS.Item(j)
        For kv = 0 To v.dao.Count
            If kv = 0 Then rg = v.ring Else rg = v.dao.Item(kv)
            m = UBound(rg, 1)
            For i = 0 To m - 1
                key = KhoaCanh(rg(i, 0), rg(i, 1), rg(i + 1, 0), rg(i + 1, 1))
                ax = ox + (rg(i, 0) - gx) * kp: ay = oy + (rg(i, 1) - gy) * kp
                bx = ox + (rg(i + 1, 0) - gx) * kp: by = oy + (rg(i + 1, 1) - gy) * kp
                If Not daVe.Exists(key) Then
                    daVe.Add key, True
                    DatLv mLvRanh
                    VeLine ax, ay, bx, by, -1
                    ' SUA 11/10/2026: khong ghi chieu dai canh tren so do (da co bang 3.3)
                End If
                s = TH_SoDinh(rg(i, 0), rg(i, 1), coKichThuoc)
                If Len(s) > 0 And Not daSo.Exists(s) Then
                    daSo.Add s, True
                    DatLv mLvSo
                    ' SUA 16/10: so hieu dinh RA NGOAI nhom thua (modViTriSo)
                    kc = cao * 0.84 * 0.8 * (0.75 + 0.3 * Len(s))
                    hx = 0.7071: hy = 0.7071
                    DC_HuongSoDinh dS, rg, m, i, (kv > 0), kc / kp, hx, hy
                    VeText ax + hx * kc, ay + hy * kc, s, cao * 0.84 * 0.8, -1
                End If
            Next i
        Next kv
    Next j

    ' Nhan thua: LoaiDat  SoThua/DienTich (giong trich luc)
    DatLv mLvNhan
    Dim caoN As Double, sLoai As String, sSo As String, sDt As String
    Dim wLoai As Double, wFrac As Double, gap As Double, lefX As Double, cx As Double, cy As Double
    caoN = cao * 0.84
    For j = 1 To dS.Count
        Set v = dS.Item(j)
        cx = ox + (v.cx - gx) * kp: cy = oy + (v.cy - gy) * kp
        sLoai = Trim$(v.loaiDat): sSo = Trim$(v.soThua): sDt = FNum(v.dt, 1)
        wLoai = Len(sLoai) * caoN * 0.6
        wFrac = Len(sDt) * caoN * 0.6
        If Len(sSo) * caoN * 0.6 > wFrac Then wFrac = Len(sSo) * caoN * 0.6
        gap = caoN * 0.4
        lefX = cx - (wLoai + gap + wFrac) / 2#
        If Len(sLoai) > 0 Then VeText lefX + wLoai / 2#, cy, sLoai, caoN, -1
        VeNhanPhanSo lefX + wLoai + gap + wFrac / 2#, cy, sSo, sDt, caoN, -1
    Next j
End Sub

' Chieu dai canh: chu xoay theo canh, dat giua canh lech sang ben phai huong ve
Private Sub VeChieuDai(ByVal ax As Double, ByVal ay As Double, ByVal bx As Double, ByVal by As Double, _
                       ByVal dai As Double, ByVal h As Double)
    Dim dx As Double, dy As Double, L As Double, ang As Double, mx As Double, my As Double
    dx = bx - ax: dy = by - ay
    L = Sqr(dx * dx + dy * dy)
    If L < h * 2# Then Exit Sub                      ' canh qua ngan tren so do
    ang = Atan2(dy, dx)
    If ang > 1.5708 Then ang = ang - 3.14159265358979
    If ang <= -1.5708 Then ang = ang + 3.14159265358979
    mx = (ax + bx) / 2# + dy / L * h * 0.8          ' phap tuyen phai (ra ngoai vong CCW)
    my = (ay + by) / 2# - dx / L * h * 0.8
    On Error Resume Next
    ActiveSettings.TextStyle.Height = h
    ActiveSettings.TextStyle.Width = h * C_TILE_W
    ActiveSettings.TextStyle.Justification = msdTextJustificationCenterCenter
    Dim oT As TextElement
    Set oT = CreateTextElement1(Nothing, FNum(dai, 2), Point3dFromXYZ(mx, my, 0#), _
                                Matrix3dFromAxisAndRotationAngle(2, ang))
    If Not oT Is Nothing Then oT.LineWeight = 0: ActiveModelReference.AddElement oT
    On Error GoTo 0
End Sub

Private Function KhoaCanh(ByVal ax As Double, ByVal ay As Double, ByVal bx As Double, ByVal by As Double) As String
    Dim a As String, b As String
    a = Format$(Round(ax, 3), "0.000") & "|" & Format$(Round(ay, 3), "0.000")
    b = Format$(Round(bx, 3), "0.000") & "|" & Format$(Round(by, 3), "0.000")
    If a < b Then KhoaCanh = a & "#" & b Else KhoaCanh = b & "#" & a
End Function

' Bang "Doan | Chieu dai": moi thua sau 1 dong tieu de (khi > 1 thua) roi cac canh
' "1-2'" | "12,34". O = chu mau "tt" (cung hang voi "cd"), sap theo cot roi tren xuong.
Private Sub DienBangDoan(ByVal sau As Collection, ByVal cxb As Double, ByVal cyb As Double, _
                         ByVal k As Double, ByVal Cpx As Double, ByVal Cpy As Double)
    Dim tX() As Double, ty() As Double, ct As Long, i As Long, hT As Double, lvT As Long
    ReDim tX(1 To gNT + 1): ReDim ty(1 To gNT + 1)
    For i = 1 To gNT
        If gTS(i) = "tt" And gTKind(i) = "TAG" Then
            ct = ct + 1: tX(ct) = gTX(i): ty(ct) = TamHang(gTX(i), gTY(i))
            hT = gTCao(i): lvT = gTL(i)
        End If
    Next i
    If ct = 0 Then Exit Sub
    SapCotHang tX, ty, ct, hT * 2#
    DatLvTag lvT

    ' danh sach dong: moi canh 1 lan (ranh ngoai roi duong cat) - modTachHop
    Dim dTT As New Collection, dCD As New Collection, j As Long, sD As String, dd As Double
    For j = 1 To TH_SoDoan()
        TH_Doan j, sD, dd
        dTT.Add sD: dCD.Add FNum(dd, 2)
    Next j

    Dim w As Double, xc As Double, xT As Double, hc As Double, r As Long
    hc = hT * k
    For r = 1 To dTT.Count
        If r > ct Then
            MsgBox "Bang chieu dai canh khong du cho (" & dTT.Count & " dong, mau co " & ct & " o).", vbExclamation, "Tach/hop thua"
            Exit For
        End If
        xc = TamCot(tX(r), ty(r), w)
        DienCell xc, ty(r), dTT.Item(r), hc, cxb, cyb, k, Cpx, Cpy, w * k
        xT = TagCanhPhai("cd", tX(r), ty(r), hT)
        If xT > -1E+29 Then
            xc = TamCot(xT, ty(r), w)
            DienCell xc, ty(r), dCD.Item(r), hc, cxb, cyb, k, Cpx, Cpy, w * k
        End If
    Next r
End Sub

Attribute VB_Name = "modKiemKe"
'============================================================
' modKiemKe - Cong cu ban do kiem ke (menu Kiem ke, kieu LandMap)
'   DC_XuatPolygonKhoanh : moi khoanh dat (vung Topology trong CSDL ban ve
'                          dang mo) -> 1 shape kin tren level chon; lo (dao)
'                          -> shape rieng cung graphic group.
'   DC_DatBangMauKK      : chon kieu bang mau khi to (ini KK_MAU 0/1)
'============================================================
Option Explicit

Private Function tieuDe() As String
    tieuDe = "Xu" & ChrW(7845) & "t Polygon khoanh " & ChrW(273) & ChrW(7845) & "t"
End Function

Public Sub DC_XuatPolygonKhoanh()
    Dim csdl As String, vungs As Collection, s As String, lv As Level
    csdl = CsdlMacDinh()
    If Len(Dir$(csdl)) > 0 Then Set vungs = MoCSDL(csdl)
    If vungs Is Nothing Then Set vungs = New Collection
    If vungs.Count = 0 Then
        DC_ThongBao "Ch" & ChrW(432) & "a c" & ChrW(243) & " d" & ChrW(7919) & " li" & ChrW(7879) & "u khoanh " & ChrW(273) & ChrW(7845) & "t (CSDL) cho b" & ChrW(7843) & "n v" & ChrW(7869) & " n" & ChrW(224) & "y:" & vbCrLf & csdl & vbCrLf & vbCrLf & _
                    "Ch" & ChrW(7841) & "y Ki" & ChrW(7875) & "m k" & ChrW(234) & " > T" & ChrW(7841) & "o l" & ChrW(7853) & "p b" & ChrW(7843) & "n " & ChrW(273) & ChrW(7891) & " ki" & ChrW(7875) & "m k" & ChrW(234) & " > T" & ChrW(7841) & "o Topology b" & ChrW(7843) & "n " & ChrW(273) & ChrW(7891) & " ki" & ChrW(7875) & "m k" & ChrW(234) & " tr" & ChrW(432) & ChrW(7899) & "c.", tieuDe, vbExclamation
        Exit Sub
    End If
    s = InputBox("Co " & vungs.Count & " khoanh dat." & vbCrLf & _
                 "Level dat polygon (TT 08 - khoanh dat: 5):", "Xuat Polygon", DC_DocCauHinh("KK_LVPOLY", "5"))
    If StrPtr(s) = 0 Or Len(Trim$(s)) = 0 Then Exit Sub
    If IsNumeric(Trim$(s)) Then Set lv = DC_LevelTheoSo(CLng(val(s))) Else Set lv = DC_TimLevel(s)
    If lv Is Nothing Then
        DC_ThongBao "Kh" & ChrW(244) & "ng t" & ChrW(236) & "m th" & ChrW(7845) & "y / kh" & ChrW(244) & "ng t" & ChrW(7841) & "o " & ChrW(273) & ChrW(432) & ChrW(7907) & "c level: " & s, tieuDe, vbExclamation
        Exit Sub
    End If
    DC_GhiCauHinh "KK_LVPOLY", Trim$(s)

    Dim i As Long, kv As Long, v As clsVung, rg() As Double, n As Long, dem As Long, bo As Long
    Dim gg As Long, o As Object
    On Error Resume Next
    CadInputQueue.SendKeyin "mark"
    Set o = ActiveDesignFile
    For i = 1 To vungs.Count
        Set v = vungs.Item(i)
        If v.HasRing Then
            gg = 0
            If v.dao.Count > 0 Then Err.Clear: gg = o.GetNextGraphicGroup: If Err.Number <> 0 Then gg = 0
            For kv = 0 To v.dao.Count
                If kv = 0 Then rg = v.ring Else rg = v.dao.Item(kv)
                If VeShape(rg, lv, gg) Then
                    If kv = 0 Then dem = dem + 1
                Else
                    If kv = 0 Then bo = bo + 1
                End If
            Next kv
        End If
    Next i
    On Error GoTo 0
    RedrawAllViews
    DC_ThongBao ChrW(272) & ChrW(227) & " xu" & ChrW(7845) & "t " & dem & " polygon khoanh " & ChrW(273) & ChrW(7845) & "t l" & ChrW(234) & "n level " & lv.Name & "." & _
                IIf(bo > 0, vbCrLf & "B" & ChrW(7887) & " qua " & bo & " khoanh (qu" & ChrW(225) & " nhi" & ChrW(7873) & "u " & ChrW(273) & ChrW(7881) & "nh ho" & ChrW(7863) & "c l" & ChrW(7895) & "i h" & ChrW(236) & "nh h" & ChrW(7885) & "c).", "") & vbCrLf & _
                "(Sai: key-in  undo mark)", tieuDe
End Sub

Private Function VeShape(rg() As Double, ByVal lv As Level, ByVal gg As Long) As Boolean
    Dim n As Long, i As Long, pts() As Point3d, sh As ShapeElement
    On Error GoTo Loi
    n = UBound(rg, 1)                     ' rg(n) = rg(0) (vong kin)
    If n < 3 Or n > 4999 Then Exit Function
    ReDim pts(0 To n)
    For i = 0 To n
        pts(i).x = rg(i, 0): pts(i).y = rg(i, 1): pts(i).Z = 0#
    Next i
    Set sh = CreateShapeElement1(Nothing, pts, msdFillModeNotFilled)
    If sh Is Nothing Then Exit Function
    Set sh.Level = lv
    On Error Resume Next
    sh.LineWeight = 0
    If gg > 0 Then sh.GraphicGroup = gg
    On Error GoTo Loi
    ActiveModelReference.AddElement sh
    VeShape = True
    Exit Function
Loi:
    VeShape = False
End Function

Public Sub DC_DatBangMauKK(ByVal kieu As String)
    DC_GhiCauHinh "KK_MAU", kieu
End Sub

'============================================================
' TO MAU BAN DO HIEN TRANG - TT 08/2024/TT-BTNMT, Phu luc V muc 9.7
'   (doi chieu file PDF Cong bao so 991+992 ngay 26/8/2024, trang 82-84)
'   Moi loai dat co SO MAU (chi so bang mau) + thong so RGB chinh thuc.
'   Bang: C:\DiaChinhVL\MauHienTrang_TT08.txt (Ma|SoMau|R|G|B), tu tao, sua duoc.
'   KK_MAU = 0 : to theo SO MAU (giu nguyen bang mau ban ve)
'   KK_MAU = 1 : pha dung RGB vao bang mau tai chinh SO MAU do roi to
'   Level mac dinh theo bang phan lop TT 08: Mau loai dat = 30, Khoanh dat = 5.
'   Khoanh lon to truoc, khoanh nho (lot trong) to sau -> nam tren.
'============================================================
Private Function MauMacDinh() As String
    MauMacDinh = "NNP:1.255.255.100,CHN:3.255.252.120,LUA:4.255.252.130,LUC:5.255.252.140,LUK:6.255.252.150,HNK:11.255.240.180,CLN:14.255.210.160,LNP:18.170.255.50,RDD:29.110.255.100,RPH:24.190.255.30,RSX:19.180.255.180,RSN:19.180.255.180,NTS:34.170.255.255,CNT:8.230.230.130,LMU:37.255.255.254,NKH:38.245.255.180,PNN:39.255.255.100,OTC:40.255.180.255,ONT:41.255.208.255,ODT:42.255.160.255,TSC:45.255.170.160,CQA:51.255.120.120,CQP:52.255.100.80,CAN:53.255.80.70,DSN:44.255.160.170,DVH:69.255.170.160,DXH:80.255.170.160,DYT:72.255.170.160,DGD:75.255.170.160,DTT:78.255.170.160,DKH:79.255.170.160,DMT:76.255.170.160,DKT:77.255.170.160," & _
                 "DNG:82.255.170.160,DSK:83.255.170.160,CSK:54.255.160.170,SCC:73.255.170.160,SKK:55.250.170.160,SKN:61.250.170.160,SCT:74.255.170.160,TMD:62.250.170.160,SKC:56.250.170.160,SKS:57.205.170.205,CCC:59.255.170.160,DGT:60.255.170.50,DTL:63.170.255.255,DCT:64.170.255.255,DPC:65.255.170.170,DDD:84.255.170.160,DRA:85.205.170.205,DNL:66.255.170.160,DBV:67.255.170.160,DCH:81.255.170.160,DKV:70.255.170.160,TON:87.255.170.160,TIN:88.255.170.160,NTD:89.210.210.210,TVC:90.180.255.255,MNC:92.180.255.255,SON:91.160.255.255,PNK:93.255.170.160,CSD:97.255.255.254,CGT:105.255.255.254,BCS:98.255.255.254,DCS:99.255.255.254,NCS:100.230.230.200,MCS:101.180.255.255"
End Function

' Ma -> Array(soMau, rgb)
Private Function DocBangMau() As Object
    Dim d As Object, f As String, a() As String, i As Long, p() As String, n As Integer, s As String, q() As String
    Set d = CreateObject("Scripting.Dictionary")
    d.CompareMode = 1
    f = DC_THUMUC & "\MauHienTrang_TT08.txt"
    On Error Resume Next
    If Len(Dir$(f)) = 0 Then
        n = FreeFile
        Open f For Output As #n
        Print #n, "' Mau loai dat ban do hien trang - TT 08/2024/TT-BTNMT Phu luc V (9.7). Dong: Ma|SoMau|R|G|B"
        a = Split(MauMacDinh(), ",")
        For i = 0 To UBound(a)
            q = Split(a(i), ":"): p = Split(q(1), ".")
            Print #n, q(0) & "|" & p(0) & "|" & p(1) & "|" & p(2) & "|" & p(3)
        Next i
        Close #n
    End If
    n = FreeFile
    Open f For Input As #n
    Do While Not EOF(n)
        Line Input #n, s
        s = Trim$(s)
        If Len(s) > 0 And Left$(s, 1) <> "'" Then
            p = Split(s, "|")
            If UBound(p) >= 4 Then d(Trim$(p(0))) = Array(CLng(val(p(1))), rgB(CLng(val(p(2))), CLng(val(p(3))), CLng(val(p(4)))))
        End If
    Loop
    Close #n
    If d.Count = 0 Then
        a = Split(MauMacDinh(), ",")
        For i = 0 To UBound(a)
            q = Split(a(i), ":"): p = Split(q(1), ".")
            d(q(0)) = Array(CLng(p(0)), rgB(CLng(p(1)), CLng(p(2)), CLng(p(3))))
        Next i
    End If
    Set DocBangMau = d
End Function

Public Sub DC_ToMauHienTrang()
    Dim csdl As String, vungs As Collection, s As String, lv As Level, bang As Object
    Dim td As String
    td = "T" & ChrW(244) & " m" & ChrW(224) & "u b" & ChrW(7843) & "n " & ChrW(273) & ChrW(7891) & " hi" & ChrW(7879) & "n tr" & ChrW(7841) & "ng"
    csdl = CsdlMacDinh()
    If Len(Dir$(csdl)) > 0 Then Set vungs = MoCSDL(csdl)
    If vungs Is Nothing Then Set vungs = New Collection
    If vungs.Count = 0 Then
        DC_ThongBao "Ch" & ChrW(432) & "a c" & ChrW(243) & " d" & ChrW(7919) & " li" & ChrW(7879) & "u khoanh " & ChrW(273) & ChrW(7845) & "t (CSDL) cho b" & ChrW(7843) & "n v" & ChrW(7869) & " n" & ChrW(224) & "y. Ch" & ChrW(7841) & "y T" & ChrW(7841) & "o Topology v" & ChrW(224) & " g" & ChrW(225) & "n lo" & ChrW(7841) & "i " & ChrW(273) & ChrW(7845) & "t tr" & ChrW(432) & ChrW(7899) & "c.", td, vbExclamation
        Exit Sub
    End If
    s = InputBox("Co " & vungs.Count & " khoanh dat. Level to mau loai dat (TT 08: 30):", "To mau hien trang", DC_DocCauHinh("KK_LVTO", "30"))
    If StrPtr(s) = 0 Or Len(Trim$(s)) = 0 Then Exit Sub
    If IsNumeric(Trim$(s)) Then Set lv = DC_LevelTheoSo(CLng(val(s))) Else Set lv = DC_TimLevel(s)
    If lv Is Nothing Then DC_ThongBao "Kh" & ChrW(244) & "ng t" & ChrW(7841) & "o " & ChrW(273) & ChrW(432) & ChrW(7907) & "c level: " & s, td, vbExclamation: Exit Sub
    DC_GhiCauHinh "KK_LVTO", Trim$(s)
    Set bang = DocBangMau()

    Dim ct As Object, rgbMode As Boolean, i As Long, v As clsVung, ma As String, daPha As Object, e As Variant
    rgbMode = (DC_DocCauHinh("KK_MAU", "0") = "1")
    Set daPha = CreateObject("Scripting.Dictionary")
    If rgbMode Then
        On Error Resume Next
        Set ct = ActiveDesignFile.ExtractColorTable
        On Error GoTo 0
    End If
    Dim thieu As String, nThieu As Long, daBao As Object
    Set daBao = CreateObject("Scripting.Dictionary"): daBao.CompareMode = 1
    For i = 1 To vungs.Count
        Set v = vungs.Item(i)
        ma = MaChinh(v.loaiDat)
        If bang.Exists(ma) Then
            e = bang(ma)
            If rgbMode And Not ct Is Nothing Then
                If Not daPha.Exists(CStr(e(0))) Then
                    On Error Resume Next
                    ct.SetColorAtIndex e(0), e(1)
                    On Error GoTo 0
                    daPha(CStr(e(0))) = True
                End If
            End If
        ElseIf Not daBao.Exists(ma) Then
            daBao(ma) = True: nThieu = nThieu + 1
            If nThieu <= 10 Then thieu = thieu & " " & IIf(Len(ma) = 0, "(trong)", ma)
        End If
    Next i
    If rgbMode And Not ct Is Nothing Then
        On Error Resume Next
        ActiveDesignFile.AttachColorTable ct
        On Error GoTo 0
    End If

    ' To: khoanh lon truoc
    Dim thuTu() As Long, j As Long, t As Long, dem As Long
    ReDim thuTu(1 To vungs.Count)
    For i = 1 To vungs.Count: thuTu(i) = i: Next i
    For i = 2 To vungs.Count
        t = thuTu(i): j = i - 1
        Do While j >= 1
            If vungs.Item(thuTu(j)).dt >= vungs.Item(t).dt Then Exit Do
            thuTu(j + 1) = thuTu(j): j = j - 1
        Loop
        thuTu(j + 1) = t
    Next i
    On Error Resume Next
    CadInputQueue.SendKeyin "mark"
    For i = 1 To vungs.Count
        Set v = vungs.Item(thuTu(i))
        ma = MaChinh(v.loaiDat)
        If bang.Exists(ma) And v.HasRing Then
            e = bang(ma)
            If ToShape(v.ring, lv, CLng(e(0))) Then dem = dem + 1
        End If
    Next i
    On Error GoTo 0
    RedrawAllViews
    DC_ThongBao ChrW(272) & ChrW(227) & " t" & ChrW(244) & " m" & ChrW(224) & "u " & dem & "/" & vungs.Count & " khoanh " & ChrW(273) & ChrW(7845) & "t (level " & lv.Name & ") theo TT 08/2024." & vbCrLf & _
                IIf(rgbMode, "Ki" & ChrW(7875) & "u: pha " & ChrW(273) & ChrW(250) & "ng RGB v" & ChrW(224) & "o b" & ChrW(7843) & "ng m" & ChrW(224) & "u t" & ChrW(7841) & "i s" & ChrW(7889) & " m" & ChrW(224) & "u quy " & ChrW(273) & ChrW(7883) & "nh.", "Ki" & ChrW(7875) & "u: t" & ChrW(244) & " theo s" & ChrW(7889) & " m" & ChrW(224) & "u quy " & ChrW(273) & ChrW(7883) & "nh (gi" & ChrW(7919) & " b" & ChrW(7843) & "ng m" & ChrW(224) & "u b" & ChrW(7843) & "n v" & ChrW(7869) & ").") & _
                IIf(nThieu > 0, vbCrLf & "Kh" & ChrW(244) & "ng c" & ChrW(243) & " m" & ChrW(224) & "u cho lo" & ChrW(7841) & "i " & ChrW(273) & ChrW(7845) & "t:" & thieu & IIf(nThieu > 10, " ...", "") & " (th" & ChrW(234) & "m v" & ChrW(224) & "o C:\DiaChinhVL\MauHienTrang_TT08.txt)", "") & vbCrLf & _
                "(Sai: key-in  undo mark)", td
End Sub

' "ONT+CLN" -> "ONT" ; bo khoang trang
Private Function MaChinh(ByVal s As String) As String
    Dim p As Long
    s = UCase$(Trim$(s))
    p = InStr(s, "+"): If p > 0 Then s = Left$(s, p - 1)
    p = InStr(s, ","): If p > 0 Then s = Left$(s, p - 1)
    MaChinh = Trim$(s)
End Function

Private Function ToShape(rg() As Double, ByVal lv As Level, ByVal mau As Long) As Boolean
    Dim n As Long, i As Long, pts() As Point3d, sh As ShapeElement, o As Object
    On Error GoTo Loi
    n = UBound(rg, 1)
    If n < 3 Or n > 4999 Then Exit Function
    ReDim pts(0 To n)
    For i = 0 To n
        pts(i).x = rg(i, 0): pts(i).y = rg(i, 1): pts(i).Z = 0#
    Next i
    Set sh = CreateShapeElement1(Nothing, pts, msdFillModeFilled)
    If sh Is Nothing Then Exit Function
    Set sh.Level = lv
    On Error Resume Next
    sh.color = mau
    sh.LineWeight = 0
    Set o = sh
    o.FillColor = mau
    On Error GoTo Loi
    ActiveModelReference.AddElement sh
    ToShape = True
    Exit Function
Loi:
    ToShape = False
End Function

Attribute VB_Name = "modKiemVung"
'============================================================
' modKiemVung - KIEM TRA VUNG THUA truoc khi giao nop Trung uong
'   Moi vung thua (ghep tu lop ranh) phai co DUNG 1 so hieu thua (lop 13),
'   1 loai dat (lop 2), 1 dien tich (lop 4) - theo bang phan lop giao nop.
'   Bao: thieu / thua (2, 3...) tung loai, tung vung. Form: frmKiemVung.
'============================================================
Option Explicit

Public KV_DsLoi As Collection        ' moi phan tu: Array(clsVung, mo ta, so thua tim thay)
' Bang dinh/canh/dau mut cho Do dau ranh lech (KV_DoDauLech)
Private dlVX() As Double, dlVY() As Double, dlVE() As Long, dlNV As Long
Private dlSX1() As Double, dlSY1() As Double, dlSX2() As Double, dlSY2() As Double, dlSE() As Long, dlNS As Long
Private dlEX() As Double, dlEY() As Double, dlEE() As Long, dlNE As Long

Public Sub DC_MoKiemVung()
    DC_MoFormTuTao "frmKiemVung"
End Sub

' Tra ve so vung ; tomTat = cau bao tong hop (kieu he thong TW)
Public Function KV_KiemTra(ByVal ranhCSV As String, ByVal lvSo As String, ByVal lvLD As String, _
                           ByVal lvDT As String, ByVal snap As Double, ByVal chiaGiao As Boolean, _
                           ByRef tomTat As String) As Long
    Dim segs As Collection, vungs As Collection, tia As Long
    Dim minX As Double, minY As Double, maxX As Double, maxY As Double
    Set KV_DsLoi = New Collection
    tomTat = ""
    If snap <= 0 Then snap = 0.05
    ShowStatus "Kiem tra vung thua: doc ranh ..."
    Set segs = LayDoanNhieuLevel(ranhCSV, snap, minX, minY, maxX, maxY)
    If segs Is Nothing Then tomTat = "Kh" & ChrW(244) & "ng " & ChrW(273) & ChrW(7885) & "c " & ChrW(273) & ChrW(432) & ChrW(7907) & "c " & ChrW(273) & ChrW(432) & ChrW(7901) & "ng ranh tr" & ChrW(234) & "n l" & ChrW(7899) & "p " & ranhCSV: Exit Function
    If segs.Count = 0 Then tomTat = "Kh" & ChrW(244) & "ng " & ChrW(273) & ChrW(7885) & "c " & ChrW(273) & ChrW(432) & ChrW(7907) & "c " & ChrW(273) & ChrW(432) & ChrW(7901) & "ng ranh tr" & ChrW(234) & "n l" & ChrW(7899) & "p " & ranhCSV: Exit Function
    If chiaGiao Then
        ShowStatus "Kiem tra vung thua: chia doan tai giao diem ..."
        Set segs = NoiDoanGiao(segs, snap)
    End If
    ShowStatus "Kiem tra vung thua: ghep vung ..."
    gGhepVungMin = 0.000001          ' SUA 05/11: giu ca vung manh (TW bao loi ca vung rat nho)
    Set vungs = GhepVung(segs, snap, tia)
    gGhepVungMin = 0#
    If vungs Is Nothing Then tomTat = "Kh" & ChrW(244) & "ng gh" & ChrW(233) & "p " & ChrW(273) & ChrW(432) & ChrW(7907) & "c v" & ChrW(249) & "ng th" & ChrW(7917) & "a n" & ChrW(224) & "o.": Exit Function
    If vungs.Count = 0 Then tomTat = "Kh" & ChrW(244) & "ng gh" & ChrW(233) & "p " & ChrW(273) & ChrW(432) & ChrW(7907) & "c v" & ChrW(249) & "ng th" & ChrW(7917) & "a n" & ChrW(224) & "o.": Exit Function

    Dim nV As Long, i As Long, j As Long
    nV = vungs.Count
    Dim bx1() As Double, by1() As Double, bx2() As Double, by2() As Double, rg() As Double
    Dim dem() As Long, soTim() As String
    ReDim bx1(1 To nV): ReDim by1(1 To nV): ReDim bx2(1 To nV): ReDim by2(1 To nV)
    ReDim dem(1 To nV, 1 To 3): ReDim soTim(1 To nV)
    For i = 1 To nV
        rg = vungs.Item(i).ring
        BaoRing rg, bx1(i), by1(i), bx2(i), by2(i)
    Next i

    ' --- gom chu tren 3 lop
    Dim lv(1 To 3) As Long, o As Level
    Set o = DC_TimLevel(lvSo): If Not o Is Nothing Then lv(1) = o.Number Else lv(1) = -99
    Set o = DC_TimLevel(lvLD): If Not o Is Nothing Then lv(2) = o.Number Else lv(2) = -99
    Set o = DC_TimLevel(lvDT): If Not o Is Nothing Then lv(3) = o.Number Else lv(3) = -99
    ShowStatus "Kiem tra vung thua: doc chu ..."
    Dim cx() As Double, cy() As Double, ck() As Long, cs() As String, nC As Long
    ReDim cx(1 To 1000): ReDim cy(1 To 1000): ReDim ck(1 To 1000): ReDim cs(1 To 1000)
    Dim esc As ElementScanCriteria, ee As ElementEnumerator
    Set esc = New ElementScanCriteria
    esc.ExcludeAllTypes
    esc.IncludeType msdElementTypeText
    esc.IncludeType msdElementTypeTextNode
    esc.IncludeType msdElementTypeCellHeader
    Set ee = ActiveModelReference.Scan(esc)
    Do While ee.MoveNext
        GomChu ee.Current, lv, cx, cy, ck, cs, nC
    Loop

    ' --- gan chu vao vung
    ShowStatus "Kiem tra vung thua: doi chieu " & nC & " chu voi " & nV & " vung ..."
    Dim v As clsVung, k As Long, coVung() As Boolean
    ReDim coVung(1 To nC + 1)
    For j = 1 To nC
        For i = 1 To nV
            If cx(j) >= bx1(i) And cx(j) <= bx2(i) And cy(j) >= by1(i) And cy(j) <= by2(i) Then
                Set v = vungs.Item(i)
                If TrongVung(v, cx(j), cy(j)) Then
                    dem(i, ck(j)) = dem(i, ck(j)) + 1
                    coVung(j) = True
                    If ck(j) = 1 Then
                        If Len(soTim(i)) > 0 Then soTim(i) = soTim(i) & ", "
                        soTim(i) = soTim(i) & cs(j)
                    End If
                    Exit For
                End If
            End If
        Next i
        If j Mod 200 = 0 Then DoEvents
    Next j

    ' --- tong hop loi
    Dim ten(1 To 3) As String, mo As String, nThieu(1 To 3) As Long, nThua(1 To 3, 2 To 9) As Long
    ten(1) = "s" & ChrW(7889) & " hi" & ChrW(7879) & "u th" & ChrW(7917) & "a": ten(2) = "lo" & ChrW(7841) & "i " & ChrW(273) & ChrW(7845) & "t": ten(3) = "di" & ChrW(7879) & "n t" & ChrW(237) & "ch"
    For i = 1 To nV
        mo = ""
        For k = 1 To 3
            If dem(i, k) = 0 Then
                mo = mo & IIf(Len(mo) > 0, "; ", "") & "thi" & ChrW(7871) & "u " & ten(k)
                nThieu(k) = nThieu(k) + 1
            ElseIf dem(i, k) > 1 Then
                mo = mo & IIf(Len(mo) > 0, "; ", "") & dem(i, k) & " " & ten(k)
                If dem(i, k) <= 9 Then nThua(k, dem(i, k)) = nThua(k, dem(i, k)) + 1 Else nThua(k, 9) = nThua(k, 9) + 1
            End If
        Next k
        If Len(mo) > 0 Then
            If vungs.Item(i).dt < 1# And dem(i, 1) = 0 Then
                mo = "V" & ChrW(217) & "NG M" & ChrW(7842) & "NH " & Format$(vungs.Item(i).dt, "0.000") & " m2 (ranh ch" & ChrW(7891) & "ng/h" & ChrW(7903) & "): " & mo
            End If
            KV_DsLoi.Add Array(vungs.Item(i), mo, soTim(i))
        End If
    Next i

    ' SUA 06/11: so thua nam NGOAI moi vung (ranh ho / vung khong ghep duoc) -> bao loi
    Dim nNgoai As Long, vN As clsVung, rN() As Double, hN As Double
    For j = 1 To nC
        If ck(j) = 1 And Not coVung(j) Then
            nNgoai = nNgoai + 1
            hN = 2#
            ReDim rN(0 To 4, 0 To 1)
            rN(0, 0) = cx(j) - hN: rN(0, 1) = cy(j) - hN
            rN(1, 0) = cx(j) + hN: rN(1, 1) = cy(j) - hN
            rN(2, 0) = cx(j) + hN: rN(2, 1) = cy(j) + hN
            rN(3, 0) = cx(j) - hN: rN(3, 1) = cy(j) + hN
            rN(4, 0) = rN(0, 0): rN(4, 1) = rN(0, 1)
            Set vN = New clsVung
            vN.ring = rN: vN.cx = cx(j): vN.cy = cy(j): vN.dt = -1#: vN.HasRing = True
            KV_DsLoi.Add Array(vN, "S" & ChrW(7889) & " th" & ChrW(7917) & "a n" & ChrW(7857) & "m NGO" & ChrW(192) & "I v" & ChrW(249) & "ng kh" & ChrW(233) & "p k" & ChrW(237) & "n (ranh h" & ChrW(7903) & " / thi" & ChrW(7871) & "u ranh chia th" & ChrW(7917) & "a)", cs(j))
        End If
    Next j

    ' SUA 07/11: TRUNG SO THUA tren cung to (TW khong chap nhan)
    Dim dTr As Object, kTr As String, nTrung As Long, sKey As Variant, idx() As String, q As Long, c As Long
    Set dTr = CreateObject("Scripting.Dictionary")
    For j = 1 To nC
        If ck(j) = 1 Then
            kTr = KV_ChuanSo(cs(j))
            If Len(kTr) > 0 Then
                If dTr.Exists(kTr) Then dTr(kTr) = dTr(kTr) & "," & j Else dTr.Add kTr, CStr(j)
            End If
        End If
    Next j
    For Each sKey In dTr.Keys
        idx = Split(dTr(sKey), ",")
        If UBound(idx) >= 1 Then
            nTrung = nTrung + 1
            For q = 0 To UBound(idx)
                c = CLng(idx(q))
                hN = 2#
                ReDim rN(0 To 4, 0 To 1)
                rN(0, 0) = cx(c) - hN: rN(0, 1) = cy(c) - hN
                rN(1, 0) = cx(c) + hN: rN(1, 1) = cy(c) - hN
                rN(2, 0) = cx(c) + hN: rN(2, 1) = cy(c) + hN
                rN(3, 0) = cx(c) - hN: rN(3, 1) = cy(c) + hN
                rN(4, 0) = rN(0, 0): rN(4, 1) = rN(0, 1)
                Set vN = New clsVung
                vN.ring = rN: vN.cx = cx(c): vN.cy = cy(c): vN.dt = -1#: vN.HasRing = True
                KV_DsLoi.Add Array(vN, "TR" & ChrW(217) & "NG s" & ChrW(7889) & " th" & ChrW(7917) & "a " & cs(c) & " (" & (q + 1) & "/" & (UBound(idx) + 1) & " tr" & ChrW(234) & "n t" & ChrW(7901) & ") - TW kh" & ChrW(244) & "ng ch" & ChrW(7845) & "p nh" & ChrW(7853) & "n", cs(c))
            Next q
        End If
    Next sKey

    Dim s As String, m As Long
    For m = 2 To 9
        s = ""
        For k = 1 To 3
            If nThua(k, m) > 0 Then s = s & IIf(Len(s) > 0, "; ", "") & "c" & ChrW(243) & " " & m & " " & ten(k)
        Next k
        If Len(s) > 0 Then tomTat = tomTat & "- v" & ChrW(249) & "ng th" & ChrW(7917) & "a " & s & " (ch" & ChrW(7881) & " " & ChrW(273) & ChrW(432) & ChrW(7907) & "c 1)" & vbCrLf
    Next m
    For k = 1 To 3
        If nThieu(k) > 0 Then tomTat = tomTat & "- " & nThieu(k) & " v" & ChrW(249) & "ng th" & ChrW(7917) & "a thi" & ChrW(7871) & "u " & ten(k) & vbCrLf
    Next k
    If nTrung > 0 Then tomTat = tomTat & "- " & nTrung & " s" & ChrW(7889) & " th" & ChrW(7917) & "a b" & ChrW(7883) & " TR" & ChrW(217) & "NG tr" & ChrW(234) & "n t" & ChrW(7901) & " (TW kh" & ChrW(244) & "ng ch" & ChrW(7845) & "p nh" & ChrW(7853) & "n)" & vbCrLf
    If nNgoai > 0 Then tomTat = tomTat & "- " & nNgoai & " s" & ChrW(7889) & " th" & ChrW(7917) & "a n" & ChrW(7857) & "m ngo" & ChrW(224) & "i v" & ChrW(249) & "ng kh" & ChrW(233) & "p k" & ChrW(237) & "n (ki" & ChrW(7875) & "m tra ranh h" & ChrW(7903) & ")" & vbCrLf
    If Len(tomTat) = 0 Then
        tomTat = ChrW(272) & ChrW(7841) & "t: " & nV & " v" & ChrW(249) & "ng th" & ChrW(7917) & "a " & ChrW(273) & ChrW(7873) & "u c" & ChrW(243) & " " & ChrW(273) & ChrW(250) & "ng 1 s" & ChrW(7889) & " hi" & ChrW(7879) & "u th" & ChrW(7917) & "a, 1 lo" & ChrW(7841) & "i " & ChrW(273) & ChrW(7845) & "t, 1 di" & ChrW(7879) & "n t" & ChrW(237) & "ch."
    Else
        tomTat = KV_DsLoi.Count & "/" & nV & " v" & ChrW(249) & "ng th" & ChrW(7917) & "a c" & ChrW(243) & " l" & ChrW(7895) & "i:" & vbCrLf & tomTat
    End If
    ShowStatus ""
    KV_KiemTra = nV
End Function

' Diem trong vung (trong ranh ngoai, ngoai cac dao)
Private Function TrongVung(ByVal v As clsVung, ByVal x As Double, ByVal y As Double) As Boolean
    Dim rg() As Double, k As Long
    rg = v.ring
    If Not DiemTrongPolygon(rg, x, y) Then Exit Function
    For k = 1 To v.dao.Count
        rg = v.dao.Item(k)
        If DiemTrongPolygon(rg, x, y) Then Exit Function
    Next k
    TrongVung = True
End Function

' Gom chu (text / text node / chu trong cell) tren 3 lop dich
Private Sub GomChu(ByVal el As Element, lv() As Long, cx() As Double, cy() As Double, _
                   ck() As Long, cs() As String, ByRef n As Long)
    Dim k As Long, s As String, sb As ElementEnumerator, lvE As Long
    On Error Resume Next
    If el.Type = msdElementTypeCellHeader Then
        Set sb = el.AsCellElement.GetSubElements
        If sb Is Nothing Then Exit Sub
        Do While sb.MoveNext
            GomChu sb.Current, lv, cx, cy, ck, cs, n
        Loop
        Exit Sub
    End If
    If el.Type <> msdElementTypeText And el.Type <> msdElementTypeTextNode Then Exit Sub
    lvE = DC_LevelSo(el)
    For k = 1 To 3
        If lvE = lv(k) Then Exit For
    Next k
    If k > 3 Then Exit Sub
    If el.Type = msdElementTypeText Then
        s = Trim$(el.AsTextElement.Text)
    Else
        Set sb = el.AsTextNodeElement.GetSubElements
        Do While sb.MoveNext
            If sb.Current.Type = msdElementTypeText Then s = s & sb.Current.AsTextElement.Text
        Loop
        s = Trim$(s)
    End If
    If Len(s) = 0 Then Exit Sub
    n = n + 1
    If n > UBound(cx) Then
        ReDim Preserve cx(1 To n * 2): ReDim Preserve cy(1 To n * 2)
        ReDim Preserve ck(1 To n * 2): ReDim Preserve cs(1 To n * 2)
    End If
    ' SUA 05/11: dung DIEM CHEN (origin) cua chu nhu he thong TW (khong dung tam khung chu)
    Dim o As Point3d
    If el.Type = msdElementTypeText Then o = el.AsTextElement.Origin Else o = el.AsTextNodeElement.Origin
    cx(n) = o.x: cy(n) = o.y
    ' SUA 07/11: theo thuc te TW - chu chi can KHONG de len ranh -> xet theo TAM khung chu
    cx(n) = (el.Range.Low.x + el.Range.High.x) / 2#
    cy(n) = (el.Range.Low.y + el.Range.High.y) / 2#
    ck(n) = k: cs(n) = s
    Err.Clear
End Sub

' Ve dau loi (cell "LOIVUNG": vong tron + chu) tai tam cac vung loi. Tra ve so dau.
Public Function KV_VeDauLoi(ByVal lvLoi As String, ByVal cao As Double) As Long
    Dim i As Long, a As Variant, v As clsVung, els(0 To 1) As Element, cel As Element, lv As Level
    If KV_DsLoi Is Nothing Then Exit Function
    If cao <= 0 Then cao = 1
    Set lv = DC_TimLevel(lvLoi)
    On Error Resume Next
    ActiveSettings.TextStyle.Height = cao: ActiveSettings.TextStyle.Width = cao
    ActiveSettings.TextStyle.Justification = msdTextJustificationLeftCenter
    For i = 1 To KV_DsLoi.Count
        a = KV_DsLoi.Item(i): Set v = a(0)
        Set els(0) = CreateEllipseElement2(Nothing, Point3dFromXYZ(v.cx, v.cy, 0#), cao * 1.5, cao * 1.5, Matrix3dIdentity)
        Set els(1) = CreateTextElement1(Nothing, CStr(a(1)), Point3dFromXYZ(v.cx + cao * 2, v.cy, 0#), Matrix3dIdentity)
        Set cel = CreateCellElement1("LOIVUNG", els, Point3dFromXYZ(v.cx, v.cy, 0#), False)
        If Not cel Is Nothing Then
            If Not lv Is Nothing Then Set cel.Level = lv
            cel.color = 3
            ActiveModelReference.AddElement cel
            If Err.Number = 0 Then KV_VeDauLoi = KV_VeDauLoi + 1
        End If
        Err.Clear
    Next i
End Function

' Xoa cac dau loi "LOIVUNG"
Public Function KV_XoaDauLoi() As Long
    Dim esc As ElementScanCriteria, ee As ElementEnumerator, dS As New Collection, i As Long
    Set esc = New ElementScanCriteria
    esc.ExcludeAllTypes
    esc.IncludeType msdElementTypeCellHeader
    Set ee = ActiveModelReference.Scan(esc)
    On Error Resume Next
    Do While ee.MoveNext
        If UCase$(ee.Current.AsCellElement.Name) = "LOIVUNG" Then dS.Add ee.Current
        Err.Clear
    Loop
    For i = 1 To dS.Count
        ActiveModelReference.RemoveElement dS.Item(i)
        If Err.Number = 0 Then KV_XoaDauLoi = KV_XoaDauLoi + 1
        Err.Clear
    Next i
End Function

'============================================================
' SUA 06/11: DO DAU RANH LECH NHO (TW coi la HO, MicroStation van tao vung duoc)
'   Dau mut cua doan ranh khong daTrung DUNG 1 dinh / khong nam DUNG tren 1 canh
'   cua doi tuong ranh khac, nhung cach < tolLech (mac dinh 1 mm).
'   Ket qua dua vao KV_DsLoi (dung chung danh sach / zoom / ve dau loi).
'============================================================

Public Function KV_DoDauLech(ByVal ranhCSV As String, ByVal tolLech As Double, ByRef tomTat As String) As Long
    Const CELL As Double = 2#
    Const SAI_TRUNG As Double = 0.000000005     ' <= 5e-9 m coi nhu daTrung khit
    Dim arr() As String, i As Long, j As Long, k As Long, lvN() As Long, nL As Long, o As Level
    Set KV_DsLoi = New Collection
    tomTat = ""
    If tolLech <= 0 Then tolLech = 0.001
    arr = Split(ranhCSV, ",")
    ReDim lvN(0 To UBound(arr) + 1)
    For i = LBound(arr) To UBound(arr)
        If Len(Trim$(arr(i))) > 0 Then
            Set o = DC_TimLevel(Trim$(arr(i)))
            If Not o Is Nothing Then lvN(nL) = o.Number: nL = nL + 1
        End If
    Next i
    If nL = 0 Then tomTat = "Kh" & ChrW(244) & "ng t" & ChrW(236) & "m th" & ChrW(7845) & "y l" & ChrW(7899) & "p ranh " & ranhCSV: Exit Function

    dlNV = 0: dlNS = 0: dlNE = 0
    ReDim dlVX(1 To 1000): ReDim dlVY(1 To 1000): ReDim dlVE(1 To 1000)
    ReDim dlSX1(1 To 1000): ReDim dlSY1(1 To 1000): ReDim dlSX2(1 To 1000): ReDim dlSY2(1 To 1000): ReDim dlSE(1 To 1000)
    ReDim dlEX(1 To 1000): ReDim dlEY(1 To 1000): ReDim dlEE(1 To 1000)

    ShowStatus "Do dau ranh lech: doc ranh ..."
    Dim esc As ElementScanCriteria, ee As ElementEnumerator, el As Element, lvE As Long, ok As Boolean
    Dim nEl As Long, pts() As Point3d, sb As ElementEnumerator, kin As Boolean
    Set esc = New ElementScanCriteria
    esc.ExcludeAllTypes
    esc.IncludeType msdElementTypeLine
    esc.IncludeType msdElementTypeLineString
    esc.IncludeType msdElementTypeShape
    esc.IncludeType msdElementTypeComplexString
    esc.IncludeType msdElementTypeComplexShape
    Set ee = ActiveModelReference.Scan(esc)
    On Error Resume Next
    Do While ee.MoveNext
        Set el = ee.Current
        lvE = el.Level.Number
        ok = False
        For k = 0 To nL - 1
            If lvE = lvN(k) Then ok = True: Exit For
        Next k
        If ok Then
            nEl = nEl + 1
            Erase pts
            kin = (el.Type = msdElementTypeShape Or el.Type = msdElementTypeComplexShape)
            If el.Type = msdElementTypeLine Or el.Type = msdElementTypeLineString Then
                pts = el.AsLineElement.GetVertices()
                DL_ThemDay pts, nEl, Not kin
            ElseIf el.Type = msdElementTypeShape Then
                pts = el.AsShapeElement.GetVertices()
                DL_ThemDay pts, nEl, False
            Else
                Set sb = Nothing
                If el.Type = msdElementTypeComplexString Then Set sb = el.AsComplexStringElement.GetSubElements Else Set sb = el.AsComplexShapeElement.GetSubElements
                Dim ax() As Double, ay() As Double, na As Long, q As Long
                na = 0: ReDim ax(1 To 64): ReDim ay(1 To 64)
                Err.Clear
                If Not sb Is Nothing Then
                Do While sb.MoveNext
                    Erase pts
                    pts = sb.Current.AsLineElement.GetVertices()
                    If Err.Number = 0 Then
                        For q = LBound(pts) To UBound(pts)
                            na = na + 1
                            If na > UBound(ax) Then ReDim Preserve ax(1 To na * 2): ReDim Preserve ay(1 To na * 2)
                            ax(na) = pts(q).x: ay(na) = pts(q).y
                        Next q
                    End If
                    Err.Clear
                Loop
                End If
                If na >= 2 Then
                    ReDim pts(0 To na - 1)
                    For q = 1 To na
                        pts(q - 1).x = ax(q): pts(q - 1).y = ay(q)
                    Next q
                    DL_ThemDay pts, nEl, Not kin
                End If
            End If
        End If
        Err.Clear
    Loop
    On Error GoTo 0
    If dlNE = 0 Then tomTat = "Kh" & ChrW(244) & "ng c" & ChrW(243) & " " & ChrW(273) & ChrW(7847) & "u m" & ChrW(250) & "t ranh n" & ChrW(224) & "o tr" & ChrW(234) & "n l" & ChrW(7899) & "p " & ranhCSV: Exit Function

    ' --- luoi o vuong cho dinh va canh
    ShowStatus "Do dau ranh lech: lap luoi ..."
    Dim dV As Object, dS As Object, key As String, ix As Long, iy As Long
    Set dV = CreateObject("Scripting.Dictionary")
    Set dS = CreateObject("Scripting.Dictionary")
    For i = 1 To dlNV
        key = CStr(Int(dlVX(i) / CELL)) & "_" & CStr(Int(dlVY(i) / CELL))
        If dV.Exists(key) Then dV(key) = dV(key) & "," & i Else dV.Add key, CStr(i)
    Next i
    Dim nb As Long, sL As Double, tt As Double, px As Double, py As Double, lastK As String
    For i = 1 To dlNS
        sL = Sqr((dlSX2(i) - dlSX1(i)) ^ 2 + (dlSY2(i) - dlSY1(i)) ^ 2)
        nb = Int(sL / (CELL * 0.5)) + 1
        lastK = ""
        For k = 0 To nb
            tt = k / nb
            px = dlSX1(i) + (dlSX2(i) - dlSX1(i)) * tt: py = dlSY1(i) + (dlSY2(i) - dlSY1(i)) * tt
            key = CStr(Int(px / CELL)) & "_" & CStr(Int(py / CELL))
            If key <> lastK Then
                If dS.Exists(key) Then dS(key) = dS(key) & "," & i Else dS.Add key, CStr(i)
                lastK = key
            End If
        Next k
        If i Mod 500 = 0 Then DoEvents
    Next i

    ' --- xet tung dau mut
    ShowStatus "Do dau ranh lech: xet " & dlNE & " dau mut ..."
    Dim ex As Double, ey As Double, g As Long, dmin As Double, d As Double, daTrung As Boolean
    Dim dsTach() As String, m As Long, dx As Long, dy As Long, nLech As Long
    Dim kq() As Double, kx() As Double, ky() As Double
    ReDim kq(1 To 16): ReDim kx(1 To 16): ReDim ky(1 To 16)
    For i = 1 To dlNE
        ex = dlEX(i): ey = dlEY(i): g = dlEE(i)
        ix = Int(ex / CELL): iy = Int(ey / CELL)
        daTrung = False
        For dx = -1 To 1
            For dy = -1 To 1
                key = CStr(ix + dx) & "_" & CStr(iy + dy)
                If dV.Exists(key) Then
                    dsTach = Split(dV(key), ",")
                    For m = 0 To UBound(dsTach)
                        j = CLng(dsTach(m))
                        If dlVE(j) <> g Then
                            If Abs(dlVX(j) - ex) <= SAI_TRUNG And Abs(dlVY(j) - ey) <= SAI_TRUNG Then daTrung = True: Exit For
                        End If
                    Next m
                End If
                If daTrung Then Exit For
            Next dy
            If daTrung Then Exit For
        Next dx
        If Not daTrung Then
            dmin = 1E+30
            For dx = -1 To 1
                For dy = -1 To 1
                    key = CStr(ix + dx) & "_" & CStr(iy + dy)
                    If dS.Exists(key) Then
                        dsTach = Split(dS(key), ",")
                        For m = 0 To UBound(dsTach)
                            j = CLng(dsTach(m))
                            If dlSE(j) <> g Then
                                d = DL_KcDoan(ex, ey, dlSX1(j), dlSY1(j), dlSX2(j), dlSY2(j))
                                If d < dmin Then dmin = d
                            End If
                        Next m
                    End If
                Next dy
            Next dx
            If dmin > SAI_TRUNG And dmin < tolLech Then
                ' bo daTrung vi tri (2 dau mut cung cho)
                ok = True
                For k = 1 To nLech
                    If Abs(kx(k) - ex) < 0.000001 And Abs(ky(k) - ey) < 0.000001 Then ok = False: Exit For
                Next k
                If ok Then
                    nLech = nLech + 1
                    If nLech > UBound(kq) Then ReDim Preserve kq(1 To nLech * 2): ReDim Preserve kx(1 To nLech * 2): ReDim Preserve ky(1 To nLech * 2)
                    kq(nLech) = dmin: kx(nLech) = ex: ky(nLech) = ey
                End If
            End If
        End If
        If i Mod 300 = 0 Then DoEvents
    Next i

    ' --- sap xep tang dan (lech cang nho cang kho thay, xep truoc)
    Dim t As Double
    For i = 1 To nLech - 1
        For j = i + 1 To nLech
            If kq(j) < kq(i) Then
                t = kq(i): kq(i) = kq(j): kq(j) = t
                t = kx(i): kx(i) = kx(j): kx(j) = t
                t = ky(i): ky(i) = ky(j): ky(j) = t
            End If
        Next j
    Next i
    Dim v As clsVung, rN() As Double, h As Double, mo As String
    h = 0.5
    For i = 1 To nLech
        ReDim rN(0 To 4, 0 To 1)
        rN(0, 0) = kx(i) - h: rN(0, 1) = ky(i) - h
        rN(1, 0) = kx(i) + h: rN(1, 1) = ky(i) - h
        rN(2, 0) = kx(i) + h: rN(2, 1) = ky(i) + h
        rN(3, 0) = kx(i) - h: rN(3, 1) = ky(i) + h
        rN(4, 0) = rN(0, 0): rN(4, 1) = rN(0, 1)
        Set v = New clsVung
        v.ring = rN: v.cx = kx(i): v.cy = ky(i): v.dt = -1#: v.HasRing = True
        If kq(i) * 1000# < 0.001 Then mo = Format$(kq(i) * 1000#, "0.0E+00") Else mo = Format$(kq(i) * 1000#, "0.000")
        mo = ChrW(272) & ChrW(7847) & "u ranh l" & ChrW(7879) & "ch " & mo & " mm (TW coi l" & ChrW(224) & " h" & ChrW(7903) & ") - b" & ChrW(7855) & "t Keypoint l" & ChrW(7841) & "i"
        KV_DsLoi.Add Array(v, mo, "X=" & Format$(kx(i), "0.000") & " Y=" & Format$(ky(i), "0.000"))
    Next i
    If nLech = 0 Then
        tomTat = ChrW(272) & ChrW(7841) & "t: " & dlNE & " " & ChrW(273) & ChrW(7847) & "u m" & ChrW(250) & "t ranh " & ChrW(273) & ChrW(7873) & "u kh" & ChrW(7899) & "p " & ChrW(273) & ChrW(250) & "ng " & ChrW(273) & ChrW(7881) & "nh/c" & ChrW(7841) & "nh (kh" & ChrW(244) & "ng c" & ChrW(243) & " " & ChrW(273) & ChrW(7847) & "u l" & ChrW(7879) & "ch d" & ChrW(432) & ChrW(7899) & "i " & Format$(tolLech * 1000#, "0.###") & " mm)."
    Else
        tomTat = nLech & " " & ChrW(273) & ChrW(7847) & "u ranh l" & ChrW(7879) & "ch nh" & ChrW(7887) & " (d" & ChrW(432) & ChrW(7899) & "i " & Format$(tolLech * 1000#, "0.###") & " mm): MicroStation v" & ChrW(7851) & "n t" & ChrW(7841) & "o v" & ChrW(249) & "ng nh" & ChrW(432) & "ng TW coi l" & ChrW(224) & " H" & ChrW(7902) & " -> 2 th" & ChrW(7917) & "a th" & ChrW(224) & "nh 1 v" & ChrW(249) & "ng." & vbCrLf & "B" & ChrW(7845) & "m t" & ChrW(7915) & "ng d" & ChrW(242) & "ng, d" & ChrW(249) & "ng Modify Element b" & ChrW(7855) & "t Keypoint (K) " & ChrW(273) & ChrW(432) & "a " & ChrW(273) & ChrW(7847) & "u m" & ChrW(250) & "t v" & ChrW(224) & "o " & ChrW(273) & ChrW(250) & "ng " & ChrW(273) & ChrW(7881) & "nh ranh b" & ChrW(234) & "n c" & ChrW(7841) & "nh."
    End If
    ShowStatus ""
    KV_DoDauLech = nLech
End Function

' Them 1 day dinh (1 doi tuong) vao bang dinh / canh / dau mut
Private Sub DL_ThemDay(pts() As Point3d, ByVal g As Long, ByVal coDauMut As Boolean)
    Dim i As Long, lo As Long, hi As Long
    On Error Resume Next
    lo = LBound(pts): hi = UBound(pts)
    If Err.Number <> 0 Then Err.Clear: Exit Sub
    On Error GoTo 0
    If hi < lo Then Exit Sub
    If Not DC_DinhHopLe(pts) Then Exit Sub      ' SUA 08/11: bo net hong toa do NaN
    For i = lo To hi
        dlNV = dlNV + 1
        If dlNV > UBound(dlVX) Then ReDim Preserve dlVX(1 To dlNV * 2): ReDim Preserve dlVY(1 To dlNV * 2): ReDim Preserve dlVE(1 To dlNV * 2)
        dlVX(dlNV) = pts(i).x: dlVY(dlNV) = pts(i).y: dlVE(dlNV) = g
        If i > lo Then
            If pts(i).x <> pts(i - 1).x Or pts(i).y <> pts(i - 1).y Then
                dlNS = dlNS + 1
                If dlNS > UBound(dlSX1) Then
                    ReDim Preserve dlSX1(1 To dlNS * 2): ReDim Preserve dlSY1(1 To dlNS * 2)
                    ReDim Preserve dlSX2(1 To dlNS * 2): ReDim Preserve dlSY2(1 To dlNS * 2): ReDim Preserve dlSE(1 To dlNS * 2)
                End If
                dlSX1(dlNS) = pts(i - 1).x: dlSY1(dlNS) = pts(i - 1).y
                dlSX2(dlNS) = pts(i).x: dlSY2(dlNS) = pts(i).y: dlSE(dlNS) = g
            End If
        End If
    Next i
    If coDauMut And hi > lo Then
        If pts(lo).x = pts(hi).x And pts(lo).y = pts(hi).y Then Exit Sub   ' day tu khep kin
        DL_ThemDau pts(lo).x, pts(lo).y, g
        DL_ThemDau pts(hi).x, pts(hi).y, g
    End If
End Sub

Private Sub DL_ThemDau(ByVal x As Double, ByVal y As Double, ByVal g As Long)
    dlNE = dlNE + 1
    If dlNE > UBound(dlEX) Then ReDim Preserve dlEX(1 To dlNE * 2): ReDim Preserve dlEY(1 To dlNE * 2): ReDim Preserve dlEE(1 To dlNE * 2)
    dlEX(dlNE) = x: dlEY(dlNE) = y: dlEE(dlNE) = g
End Sub

' Khoang cach diem (px,py) toi doan AB - tinh theo toa do tuong doi de giu do chinh xac
Private Function DL_KcDoan(ByVal px As Double, ByVal py As Double, ByVal ax As Double, ByVal ay As Double, _
                           ByVal bx As Double, ByVal by As Double) As Double
    Dim ux As Double, uy As Double, wx As Double, wy As Double, L2 As Double, t As Double
    ux = bx - ax: uy = by - ay
    wx = px - ax: wy = py - ay
    L2 = ux * ux + uy * uy
    If L2 <= 0# Then DL_KcDoan = Sqr(wx * wx + wy * wy): Exit Function
    t = (wx * ux + wy * uy) / L2
    If t < 0# Then t = 0#
    If t > 1# Then t = 1#
    wx = wx - t * ux: wy = wy - t * uy
    DL_KcDoan = Sqr(wx * wx + wy * wy)
End Function

' Chuan hoa so thua de so trung: bo khoang trang, ky tu dieu khien
Private Function KV_ChuanSo(ByVal t As String) As String
    Dim i As Long, ch As String, r As String
    For i = 1 To Len(t)
        ch = Mid$(t, i, 1)
        If AscW(ch) > 32 Then r = r & ch
    Next i
    KV_ChuanSo = UCase$(r)
End Function

Attribute VB_Name = "modLevel"
'============================================================
' modLevel - Tim level theo SO hoac TEN
'   "13"        -> level co Number = 13
'   "Level 13"  -> tim theo ten; khong co ten do thi lay so 13
'   "Ranh thua" -> tim theo ten
'============================================================
Option Explicit

' Mac dinh giong gCadas: Level ho so = cac level cua file mau,
' Level so do = canh thua, so hieu dinh, nhan thua
Public Const DC_LV_HS_MD As String = "24,56,60,61"
Public Const DC_LV_SD_MD As String = "37,38,30"

Public Function DC_TimLevel(ByVal s As String) As Level
    Dim t As String, lv As Level, n As Long
    t = Trim$(s)
    If Len(t) = 0 Then Exit Function

    If IsNumeric(t) Then
        Set DC_TimLevel = TimTheoSo(CLng(val(t)))
        Exit Function
    End If

    On Error Resume Next
    Set lv = ActiveModelReference.Levels(t)
    On Error GoTo 0
    If Not lv Is Nothing Then Set DC_TimLevel = lv: Exit Function

    If LCase$(Left$(t, 6)) = "level " Then
        If IsNumeric(Trim$(Mid$(t, 7))) Then Set DC_TimLevel = TimTheoSo(CLng(val(Mid$(t, 7))))
    End If
End Function

'--- so level cua 1 phan tu (-1 neu khong doc duoc)
Public Function DC_LevelSo(ByVal el As Element) As Long
    DC_LevelSo = -1
    On Error Resume Next
    DC_LevelSo = el.Level.Number
End Function

Private Function TimTheoSo(ByVal n As Long) As Level
    Dim lv As Level
    For Each lv In ActiveModelReference.Levels
        If lv.Number = n Then Set TimTheoSo = lv: Exit Function
    Next lv
End Function

'--- Level theo SO; chua co thi tao moi "Level n"
Public Function DC_LevelTheoSo(ByVal n As Long) As Level
    Dim lv As Level
    If n <= 0 Then Exit Function
    Set lv = TimTheoSo(n)
    If lv Is Nothing Then
        On Error Resume Next
        Set lv = ActiveDesignFile.AddNewLevel("Level " & n)
        If Not lv Is Nothing Then
            lv.Number = n
            ActiveDesignFile.Levels.Rewrite
        End If
        Err.Clear
        Set lv = TimTheoSo(n)
        If lv Is Nothing Then Set lv = ActiveModelReference.Levels("Level " & n)
        Err.Clear
        On Error GoTo 0
    End If
    Set DC_LevelTheoSo = lv
End Function

'--- "24,56,60,61" / "Level 37; Level 38" -> mang so level, tra ve so phan tu
Public Function DC_DsSoLevel(ByVal s As String, ByRef dS() As Long) As Long
    Dim t As String, a() As String, i As Long, c As Long, v As String
    t = LCase$(s)
    t = Replace(t, "level", " ")
    t = Replace(t, ";", ","): t = Replace(t, "/", ",")
    a = Split(t, ",")
    ReDim dS(0 To UBound(a) + 1)
    For i = 0 To UBound(a)
        v = Trim$(a(i))
        If Len(v) > 0 And IsNumeric(v) Then
            If CLng(val(v)) > 0 Then dS(c) = CLng(val(v)): c = c + 1
        End If
    Next i
    DC_DsSoLevel = c
End Function

Attribute VB_Name = "modLoaiDat"
Option Explicit

'============================================================
' modLoaiDat - Loai dat + nhan thua day du (so thua / dt / loai dat)
' Tu chua, dung lai TimThuaChua (modThuocTinh) va VeText/VeLine.
'============================================================


'============================================================
' Bang mau theo loai dat (port MA_LOAI_DAT). Tra -1 neu khong co.
'============================================================
Public Function MauLoaiDat(ByVal loai As String) As Long
    Select Case UCase$(Trim$(loai))
        Case "ODT", "ONT":        MauLoaiDat = 2
        Case "CLN":               MauLoaiDat = 3
        Case "CHN":               MauLoaiDat = 58
        Case "LUA", "LUC":        MauLoaiDat = 62
        Case "NTS":               MauLoaiDat = 1
        Case "TNN":               MauLoaiDat = 45
        Case "RSX":               MauLoaiDat = 4
        Case "RPH":               MauLoaiDat = 49
        Case "RDD":               MauLoaiDat = 64
        Case "SKK":               MauLoaiDat = 11
        Case "MNC":               MauLoaiDat = 9
        Case "DGT":               MauLoaiDat = 7
        Case "CSD":               MauLoaiDat = 42
        Case "ANQ":               MauLoaiDat = 38
        Case "TON":               MauLoaiDat = 70
        Case "BDT":               MauLoaiDat = 65
        Case Else:                MauLoaiDat = -1
    End Select
End Function


'============================================================
' Doc 1 phan tu text (Text hoac TextNode) -> (x, y, chuoi)
'============================================================
Private Function DocMotText(ByVal el As Element, ByRef x As Double, _
                            ByRef y As Double, ByRef s As String) As Boolean
    DocMotText = False
    s = ""
    Dim o As Point3d
    If el.Type = msdElementTypeText Then
        Dim oT As TextElement
        Set oT = el
        o = oT.Origin
        x = o.x: y = o.y
        s = Trim$(oT.Text)
        DocMotText = True
    ElseIf el.Type = msdElementTypeTextNode Then
        Dim oNode As TextNodeElement
        Set oNode = el
        o = oNode.Origin
        x = o.x: y = o.y
        Dim subs As ElementEnumerator
        Set subs = oNode.GetSubElements
        Do While subs.MoveNext
            If subs.Current.Type = msdElementTypeText Then
                s = Trim$(subs.Current.AsTextElement.Text)
                If Len(s) > 0 Then Exit Do
            End If
        Loop
        DocMotText = True
    End If
End Function

Private Function LayTruong(ByVal v As clsVung, ByVal truong As String) As String
    Select Case truong
        Case "so_thua":  LayTruong = v.soThua
        Case "loai_dat": LayTruong = v.loaiDat
        Case "ten_chu":  LayTruong = v.TenChu
    End Select
End Function

Private Sub DatTruong(ByVal v As clsVung, ByVal truong As String, ByVal GiaTri As String)
    Select Case truong
        Case "so_thua":  v.soThua = GiaTri
        Case "loai_dat": v.loaiDat = GiaTri
        Case "ten_chu":  v.TenChu = GiaTri
    End Select
End Sub


'============================================================
' Gan gia tri text tren mot level vao truong tuong ung cua thua chua no.
' Tra ve so thua gan duoc.
'============================================================
Public Function GanTruong(ByVal vungs As Collection, ByVal levelName As String, _
                          ByVal truong As String) As Long
    Dim esc As ElementScanCriteria
    Set esc = New ElementScanCriteria
    esc.ExcludeAllTypes
    esc.IncludeType msdElementTypeText
    esc.IncludeType msdElementTypeTextNode
    If Len(Trim$(levelName)) > 0 Then
        Dim lv As Level
        On Error Resume Next
        Set lv = ActiveModelReference.Levels(levelName)
        On Error GoTo 0
        If Not lv Is Nothing Then esc.ExcludeAllLevels: esc.IncludeLevel lv
    End If

    Dim ee As ElementEnumerator
    Set ee = ActiveModelReference.Scan(esc)
    Dim x As Double, y As Double, s As String, v As clsVung, dem As Long
    Do While ee.MoveNext
        If DocMotText(ee.Current, x, y, s) Then
            If Len(s) > 0 Then
                Set v = TimThuaChua(vungs, x, y)
                If Not v Is Nothing Then
                    If Len(LayTruong(v, truong)) = 0 Then
                        DatTruong v, truong, s
                        dem = dem + 1
                    End If
                End If
            End If
        End If
    Loop
    GanTruong = dem
End Function


'============================================================
' Ve nhan thua day du - kieu phan so dia chinh:
'   so thua (tren) / dien tich (duoi), loai dat ben trai, gach ngang giua.
'   maDung: "mau" = to mau theo loai dat ; "khong" = giu mau active.
'============================================================
Public Sub VeNhanThuaDayDu(ByVal v As clsVung, ByVal cao As Double, _
                           Optional ByVal maDung As String = "khong")
    Dim mau As Long
    mau = -1
    If maDung = "mau" Then
        Dim m As Long
        m = MauLoaiDat(v.loaiDat)
        If m >= 0 Then mau = m
    End If

    Dim tu As String, duoiS As String, loai As String
    tu = Trim$(v.soThua)
    duoiS = Replace(Format$(Round(v.dt, 1), "0.0"), ".", ",")
    loai = Trim$(v.loaiDat)

    Dim wTu As Double, wMau As Double, rong As Double, nua As Double
    wTu = Len(tu) * cao * 0.6
    wMau = Len(duoiS) * cao * 0.6
    rong = wTu
    If wMau > rong Then rong = wMau
    nua = rong / 2# + cao * 0.2

    ' Gach ngang giua
    VeLine v.cx - nua, v.cy, v.cx + nua, v.cy, mau
    ' So thua tren
    If Len(tu) > 0 Then VeText v.cx, v.cy + cao * 0.9, tu, cao, mau
    ' Dien tich duoi
    If Len(duoiS) > 0 Then VeText v.cx, v.cy - cao * 0.9, duoiS, cao, mau
    ' Loai dat ben trai, ngang muc gach
    If Len(loai) > 0 Then
        Dim wl As Double
        wl = Len(loai) * cao * 0.6
        VeText v.cx - nua - wl / 2# - cao * 0.3, v.cy, loai, cao, mau
    End If
End Sub


Private Function TenLevelActive() As String
    On Error Resume Next
    TenLevelActive = ActiveSettings.Level.Name
    On Error GoTo 0
End Function

Private Function CoChuUocLuong(ByVal minX As Double, ByVal minY As Double, _
                               ByVal maxX As Double, ByVal maxY As Double) As Double
    Dim s As Double
    s = ((maxX - minX) + (maxY - minY)) / 2# / 1500#
    If s <= 0# Then s = 1#
    CoChuUocLuong = s
End Function


'============================================================
' LENH TONG HOP: GAN SO THUA + LOAI DAT (+ TEN CHU) + VE NHAN DAY DU
'============================================================
Public Sub DC_GanNhanDayDu()
    Dim lvRanh As String, lvSo As String, lvLoai As String, lvChu As String
    Dim snapStr As String, snap As Double

    lvRanh = InputBox("TEN level RANH thua:", "Gan nhan day du", TenLevelActive())
    lvSo = InputBox("TEN level SO THUA:", "Gan nhan day du", "")
    lvLoai = InputBox("TEN level LOAI DAT:" & vbCrLf & "(De trong = bo qua)", _
                      "Gan nhan day du", "")
    lvChu = InputBox("TEN level TEN CHU:" & vbCrLf & "(De trong = bo qua)", _
                     "Gan nhan day du", "")
    snapStr = InputBox("Dung sai noi diem (snap):", "Gan nhan day du", "0.05")
    If snapStr = "" Then Exit Sub
    snap = val(snapStr)
    If snap <= 0 Then snap = 0.05

    ' Doc ranh + ghep vung
    Dim minX As Double, minY As Double, maxX As Double, maxY As Double
    Dim segs As Collection
    Set segs = LayCacDoan(snap, lvRanh, minX, minY, maxX, maxY)
    If segs.Count = 0 Then
        MsgBox "Khong doc duoc doan ranh nao.", vbExclamation, "Gan nhan day du"
        Exit Sub
    End If
    Dim soTia As Long, vungs As Collection
    Set vungs = GhepVung(segs, snap, soTia)
    If vungs.Count = 0 Then
        MsgBox "Khong ghep duoc vung nao.", vbExclamation, "Gan nhan day du"
        Exit Sub
    End If

    ' Gan cac truong
    Dim nSo As Long, nLoai As Long, nChu As Long
    nSo = GanTruong(vungs, lvSo, "so_thua")
    If Len(Trim$(lvLoai)) > 0 Then nLoai = GanTruong(vungs, lvLoai, "loai_dat")
    If Len(Trim$(lvChu)) > 0 Then nChu = GanTruong(vungs, lvChu, "ten_chu")

    ' Hoi co chu + mau
    Dim caoStr As String, cao As Double
    cao = CoChuUocLuong(minX, minY, maxX, maxY)
    caoStr = InputBox("Co chu nhan (chieu cao):", "Gan nhan day du", Format$(cao, "0.###"))
    If caoStr <> "" Then cao = val(caoStr)
    If cao <= 0 Then cao = 1

    Dim mauStr As String, maDung As String
    mauStr = InputBox("To mau nhan theo loai dat? (c/k):", "Gan nhan day du", "k")
    If LCase$(Trim$(mauStr)) = "c" Then maDung = "mau" Else maDung = "khong"

    ' Ve nhan
    Dim i As Long, v As clsVung
    For i = 1 To vungs.Count
        Set v = vungs.Item(i)
        VeNhanThuaDayDu v, cao, maDung
    Next i

    MsgBox "So thua (vung): " & vungs.Count & vbCrLf & _
           "Gan so thua: " & nSo & vbCrLf & _
           "Gan loai dat: " & nLoai & vbCrLf & _
           "Gan ten chu: " & nChu, _
           vbInformation, "Gan nhan day du"
End Sub

Attribute VB_Name = "modMaXa"
Option Explicit

'============================================================
' modMaXa - Nap danh sach Tinh/Xa tu file MaXaVN.txt (UTF-8)
' Moi dong: tenTinh <TAB> tenXa
'============================================================
Private gTinh() As String
Private gXa() As String
Private gN As Long
Private gDaNap As Boolean

Public Function NapMaXa(ByVal path As String) As Boolean
    NapMaXa = False
    Dim st As Object
    On Error Resume Next
    Set st = CreateObject("ADODB.Stream")
    On Error GoTo 0
    If st Is Nothing Then Exit Function
    st.Type = 2: st.Charset = "utf-8": st.Open
    On Error Resume Next
    st.LoadFromFile path
    If Err.Number <> 0 Then st.Close: Exit Function
    On Error GoTo 0
    Dim txt As String
    txt = st.ReadText(-1): st.Close

    Dim raw() As String, i As Long, p As Long
    raw = Split(txt, vbLf)
    ReDim gTinh(0 To UBound(raw))
    ReDim gXa(0 To UBound(raw))
    gN = 0
    For i = LBound(raw) To UBound(raw)
        If Len(Trim$(raw(i))) > 0 Then
            p = InStr(raw(i), vbTab)
            If p > 0 Then
                gTinh(gN) = Left$(raw(i), p - 1)
                gXa(gN) = Trim$(Mid$(raw(i), p + 1))
                gN = gN + 1
            End If
        End If
    Next i
    gDaNap = (gN > 0)
    NapMaXa = gDaNap
End Function

' Danh sach tinh (khong trung, giu thu tu xuat hien)
Public Function DsTinh() As Collection
    Dim c As New Collection, d As Object, i As Long
    Set d = CreateObject("Scripting.Dictionary")
    For i = 0 To gN - 1
        If Not d.Exists(gTinh(i)) Then
            d.Add gTinh(i), True
            c.Add gTinh(i)
        End If
    Next i
    Set DsTinh = c
End Function

' Danh sach xa cua 1 tinh
Public Function DsXa(ByVal tinh As String) As Collection
    Dim c As New Collection, i As Long
    For i = 0 To gN - 1
        If gTinh(i) = tinh Then c.Add gXa(i)
    Next i
    Set DsXa = c
End Function

Public Function DaNapMaXa() As Boolean
    DaNapMaXa = gDaNap
End Function

Attribute VB_Name = "modMauDgn"
'============================================================
' modMauDgn - Dung file MAU .dgn (kieu gCadas) cho trich luc
'   - DC_ChuanBiMau: "File mau" la .dgn -> tu bat mau ra
'       C:\DiaChinhVL\Mau\<ten>_mau_v4.txt (chi lam lai khi .dgn/.ini doi)
'   - Doc .dgn bang OpenDesignFileForProgram (khong mo len man hinh)
'   - Lay TOAN BO file mau (moi trang: KQ do dac, Trich luc, Ho so...).
'     Trang Trich luc (co o so do level LevelKhungSoDoHinhThe) duoc dien
'     so do + bang toa do; cac trang khac ve nguyen de nguoi dung tu lam.
'   - Placeholder (soHieuThua, dienTich, tttl...) -> TAG o moi trang
'   - Chu font VnTime (TCVN3) -> doi sang Unicode
'   - Quy doi kich thuoc ve chuan mau cu (o so do rong 989.8 don vi)
'   - Cau hinh: file .ini kieu gCadas ([Levels])
'============================================================
Option Explicit

Private Type OPENFILENAME
    lStructSize As Long
    hwndOwner As Long
    hInstance As Long
    lpstrFilter As String
    lpstrCustomFilter As String
    nMaxCustFilter As Long
    nFilterIndex As Long
    lpstrFile As String
    nMaxFile As Long
    lpstrFileTitle As String
    nMaxFileTitle As Long
    lpstrInitialDir As String
    lpstrTitle As String
    flags As Long
    nFileOffset As Integer
    nFileExtension As Integer
    lpstrDefExt As String
    lCustData As Long
    lpfnHook As Long
    lpTemplateName As String
End Type
Private Declare Function GetOpenFileNameA Lib "comdlg32.dll" (pOpenfilename As OPENFILENAME) As Long
Private Declare Function GetSaveFileNameA Lib "comdlg32.dll" (pOpenfilename As OPENFILENAME) As Long

' Level ho so: nhap 1 so -> moi phan tu chep tu mau ve level do; nhieu so / tat -> giu level cua mau
Public gLvHSMot As Level
' Level ho so NHIEU so: level mau (so) -> level xuat; level mau khong co trong bang -> gLvHSMot
Public gLvHSMap As Object

Private Const BOX_CHUAN As Double = 989.8      ' be rong o so do mau chuan (TT26)
Private Const TCVN_MAP As String = "A10102,A200C2,A300CA,A400D4,A501A0,A601AF,A70110,A80103,A900E2,AA00EA,AB00F4,AC01A1,AD01B0,AE0111,B500E0,B61EA3,B700E3,B800E1,B91EA1,BB1EB1,BC1EB3,BD1EB5,BE1EAF,C61EB7,C71EA7,C81EA9,C91EAB,CA1EA5,CB1EAD,CC00E8,CE1EBB,CF1EBD,D000E9,D11EB9,D21EC1,D31EC3,D41EC5,D51EBF,D61EC7,D700EC,D81EC9,DC0129,DD00ED,DE1ECB,DF00F2,E11ECF,E200F5,E300F3,E41ECD,E51ED3,E61ED5,E71ED7,E81ED1,E91ED9,EA1EDD,EB1EDF,EC1EE1,ED1EDB,EE1EE3,EF00F9,F11EE7,F20169,F300FA,F41EE5,F51EEB,F61EED,F71EEF,F81EE9,F91EF1,FA1EF3,FB1EF7,FC1EF9,FD00FD,FE1EF5"

Private mBuf() As String, mN As Long
Private mS As Double                            ' he so quy doi
Private mLvND As Long, mLvBox As Long
Private mWx1 As Double, mWy1 As Double, mWx2 As Double, mWy2 As Double
Private mBx1 As Double, mBy1 As Double, mBx2 As Double, mBy2 As Double
Private mMinX As Double, mMinY As Double, mMaxX As Double, mMaxY As Double
Private mNL As Long, mNT As Long, mCoBB As Boolean
Private mTcvn(0 To 255) As Long, mTcvnNap As Boolean
' SUA 22/10: gop dong chu tach/hop (ID phan tu mau -> chu gop ; Chr(1) = bo)
Private mGop As Object
' SUA 22/10: chu/so lieu DIEN THEM vao mau ve 1 mau rieng (khac mau khung)
'   DiaChinhVL.ini: TL_MAUDIEN = so mau (mac dinh 1) ; -1 = tat
Public gMauDienCu As Long, gDoiMauDien As Boolean

'============================================================
' Hop thoai chon file (Windows)
'   loc vd: "File mau (*.dgn;*.txt)|*.dgn;*.txt"
'============================================================
Public Function DC_ChonFile(ByVal loc As String, ByVal tieuDe As String, _
                            Optional ByVal fileCu As String = "") As String
    Dim o As OPENFILENAME, r As Long, p As Long
    o.lStructSize = Len(o)
    o.lpstrFilter = Replace(loc, "|", vbNullChar) & vbNullChar & vbNullChar
    o.lpstrFile = String$(1024, vbNullChar)
    o.nMaxFile = 1024
    If Len(fileCu) > 0 Then
        p = InStrRev(fileCu, "\")
        If p > 0 Then o.lpstrInitialDir = Left$(fileCu, p - 1)
    End If
    o.lpstrTitle = tieuDe
    o.flags = &H1000 Or &H800 Or &H4             ' FILEMUSTEXIST, PATHMUSTEXIST, HIDEREADONLY
    r = GetOpenFileNameA(o)
    If r <> 0 Then
        p = InStr(o.lpstrFile, vbNullChar)
        If p > 0 Then DC_ChonFile = Left$(o.lpstrFile, p - 1) Else DC_ChonFile = o.lpstrFile
    End If
End Function

'============================================================
' Tra ve duong dan file mau .txt de ve khung.
'   .txt -> giu nguyen ; .dgn -> bat mau (co cache)
'============================================================
Public Function DC_ChuanBiMau(ByVal mauPath As String, Optional ByVal iniPath As String = "#") As String
    Dim ini As String, outF As String, ten As String, p As Long
    DC_ChuanBiMau = mauPath
    If LCase$(Right$(Trim$(mauPath), 4)) <> ".dgn" Then Exit Function
    If Len(Dir$(mauPath)) = 0 Then
        DC_ThongBao "Kh" & ChrW(244) & "ng th" & ChrW(7845) & "y file m" & ChrW(7851) & "u: " & mauPath, "Tr" & ChrW(237) & "ch l" & ChrW(7909) & "c", vbExclamation
        Exit Function
    End If
    ' SUA 11/10/2026: tach/hop thua truyen ini rieng (22tach.ini...)
    If iniPath = "#" Then ini = DC_DocCauHinh("INI_TL", "") Else ini = Trim$(iniPath)
    If Len(ini) > 0 And Len(Dir$(ini)) = 0 Then ini = ""

    ten = Mid$(mauPath, InStrRev(mauPath, "\") + 1)
    p = InStrRev(ten, "."): If p > 0 Then ten = Left$(ten, p - 1)
    On Error Resume Next
    If Len(Dir$(DC_THUMUC, vbDirectory)) = 0 Then MkDir DC_THUMUC
    If Len(Dir$(DC_THUMUC & "\Mau", vbDirectory)) = 0 Then MkDir DC_THUMUC & "\Mau"
    On Error GoTo 0
    outF = DC_THUMUC & "\Mau\" & ten & "_mau_v5.txt"

    ' Cache: dung lai khi CUNG duong dan .dgn + .ini va file .txt moi hon ca hai.
    ' SUA 09/10/2026: truoc chi so ten file -> doi sang tluc.dgn o thu muc khac
    ' van dung cache cua file cu (chep phan tu tu file cu -> lech).
    If Len(Dir$(outF)) > 0 Then
        If Not CacheCungFile(outF, mauPath, ini) Then
            On Error Resume Next
            Kill outF
            On Error GoTo 0
        End If
    End If
    If Len(Dir$(outF)) > 0 Then
        If FileDateTime(outF) >= FileDateTime(mauPath) Then
            If Len(ini) = 0 Then
                DC_ChuanBiMau = outF: Exit Function
            ElseIf FileDateTime(outF) >= FileDateTime(ini) Then
                DC_ChuanBiMau = outF: Exit Function
            End If
        End If
    End If

    If BatMauDgn(mauPath, ini, outF) Then DC_ChuanBiMau = outF
End Function

' Dong H cua cache: ... DGN <mS> <duong dan .dgn> <duong dan .ini>
Private Function CacheCungFile(ByVal outF As String, ByVal dgn As String, ByVal ini As String) As Boolean
    Dim st As Object, L As String, parts() As String
    On Error GoTo Loi
    Set st = CreateObject("ADODB.Stream")
    st.Type = 2: st.Charset = "utf-8": st.Open
    st.LineSeparator = 10        ' adLF
    st.LoadFromFile outF
    L = st.ReadText(-2)          ' 1 dong
    st.Close
    L = Replace(L, vbCr, "")
    If Left$(L, 1) = ChrW(&HFEFF) Then L = Mid$(L, 2)
    parts = Split(L, vbTab)
    If UBound(parts) < 9 Then Exit Function
    If LCase$(Trim$(parts(8))) <> LCase$(Trim$(dgn)) Then Exit Function
    If LCase$(Trim$(parts(9))) <> LCase$(Trim$(ini)) Then Exit Function
    CacheCungFile = True
    Exit Function
Loi:
    CacheCungFile = False
End Function

' Bat lai mau ngay (menu / nut "Bat lai mau")
Public Sub DC_BatLaiMau()
    Dim mau As String, outF As String, ten As String, p As Long
    mau = DC_DocCauHinh("MAU_TL", "")
    If LCase$(Right$(mau, 4)) <> ".dgn" Then
        DC_ThongBao "File m" & ChrW(7851) & "u hi" & ChrW(7879) & "n t" & ChrW(7841) & "i kh" & ChrW(244) & "ng ph" & ChrW(7843) & "i .dgn.", "B" & ChrW(7855) & "t m" & ChrW(7851) & "u", vbExclamation
        Exit Sub
    End If
    ten = Mid$(mau, InStrRev(mau, "\") + 1)
    p = InStrRev(ten, "."): If p > 0 Then ten = Left$(ten, p - 1)
    outF = DC_THUMUC & "\Mau\" & ten & "_mau_v5.txt"
    On Error Resume Next
    If Len(Dir$(outF)) > 0 Then Kill outF
    On Error GoTo 0
    If DC_ChuanBiMau(mau) = outF Then
        DC_ThongBao ChrW(272) & ChrW(227) & " b" & ChrW(7855) & "t m" & ChrW(7851) & "u: " & mNL & " " & ChrW(273) & ChrW(432) & ChrW(7901) & "ng, " & mNT & " ch" & ChrW(7919) & "." & vbCrLf & outF, "B" & ChrW(7855) & "t m" & ChrW(7851) & "u"
    End If
End Sub

'============================================================
Private Function BatMauDgn(ByVal dgn As String, ByVal ini As String, ByVal outF As String) As Boolean
    Dim f As DesignFile, md As ModelReference
    Dim esc As ElementScanCriteria, ee As ElementEnumerator

    mLvND = SoLevel(DocIni(ini, "Levels", "LevelNoiDung", "Level 56"), 56)
    mLvBox = SoLevel(DocIni(ini, "Levels", "LevelKhungSoDoHinhThe", "Level 24"), 24)

    On Error Resume Next
    Set f = Application.OpenDesignFileForProgram(dgn, True)
    On Error GoTo 0
    If f Is Nothing Then
        DC_ThongBao "Kh" & ChrW(244) & "ng m" & ChrW(7903) & " " & ChrW(273) & ChrW(432) & ChrW(7907) & "c file m" & ChrW(7851) & "u .dgn:" & vbCrLf & dgn, "B" & ChrW(7855) & "t m" & ChrW(7851) & "u", vbExclamation
        Exit Function
    End If
    Set md = f.DefaultModelReference

    ' 1) Tim o so do (shape lon nhat tren level o so do) -> cua so trang Trich luc
    Dim bx1 As Double, by1 As Double, bx2 As Double, by2 As Double
    If Not TimOSoDo(md, bx1, by1, bx2, by2) Then
        DC_ThongBao "Kh" & ChrW(244) & "ng t" & ChrW(236) & "m th" & ChrW(7845) & "y " & ChrW(244) & " s" & ChrW(417) & " " & ChrW(273) & ChrW(7891) & " (level " & mLvBox & ") trong file m" & ChrW(7851) & "u.", "B" & ChrW(7855) & "t m" & ChrW(7851) & "u", vbExclamation
        f.Close
        Exit Function
    End If
    Dim bw As Double, bh As Double
    bw = bx2 - bx1: bh = by2 - by1
    mS = BOX_CHUAN / bw                      ' quy doi ve chuan mau cu
    mBx1 = bx1: mBy1 = by1: mBx2 = bx2: mBy2 = by2
    ' lay toan bo file (khong gioi han cua so)
    mWx1 = -1E+30: mWx2 = 1E+30: mWy1 = -1E+30: mWy2 = 1E+30

    ' 2) Quet tat ca phan tu trong cua so
    mN = 0: ReDim mBuf(0 To 1023)
    mNL = 0: mNT = 0: mCoBB = False
    Set esc = New ElementScanCriteria
    esc.ExcludeAllTypes
    esc.IncludeType msdElementTypeLine
    esc.IncludeType msdElementTypeLineString
    esc.IncludeType msdElementTypeShape
    esc.IncludeType msdElementTypeComplexString
    esc.IncludeType msdElementTypeComplexShape
    esc.IncludeType msdElementTypeText
    esc.IncludeType msdElementTypeTextNode
    esc.IncludeType msdElementTypeCellHeader
    Set ee = md.Scan(esc)
    Do While ee.MoveNext
        ThemPhanTu ee.Current, -1
    Loop
    f.Close

    If mNL = 0 Then
        DC_ThongBao "Kh" & ChrW(244) & "ng " & ChrW(273) & ChrW(7885) & "c " & ChrW(273) & ChrW(432) & ChrW(7907) & "c " & ChrW(273) & ChrW(432) & ChrW(7901) & "ng n" & ChrW(224) & "o trong trang Tr" & ChrW(237) & "ch l" & ChrW(7909) & "c c" & ChrW(7911) & "a file m" & ChrW(7851) & "u.", "B" & ChrW(7855) & "t m" & ChrW(7851) & "u", vbExclamation
        Exit Function
    End If

    ' 3) Ghi file
    Dim txt As String
    ' H: ... DGN <he so quy doi> <duong dan .dgn>  (modKhungMau chep thang phan tu tu .dgn)
    txt = "H" & vbTab & "100.0" & vbTab & s2(mMinX) & vbTab & s2(mMinY) & vbTab & _
          s2(mMaxX) & vbTab & s2(mMaxY) & vbTab & "DGN" & vbTab & s2(mS) & vbTab & dgn & vbTab & ini & vbLf & JoinBuf()
    BatMauDgn = GhiUtf8(outF, txt)
End Function

' Shape lon nhat tren level o so do (gom ca line tao thanh hinh chu nhat)
Private Function TimOSoDo(ByVal md As ModelReference, ByRef x1 As Double, ByRef y1 As Double, _
                          ByRef x2 As Double, ByRef y2 As Double) As Boolean
    Dim esc As ElementScanCriteria, ee As ElementEnumerator, el As Element
    Dim rg As Range3d, a As Double, best As Double
    Dim ax As Double, ay As Double, bx As Double, by As Double
    Set esc = New ElementScanCriteria
    esc.ExcludeAllTypes
    esc.IncludeType msdElementTypeShape
    esc.IncludeType msdElementTypeLineString
    esc.IncludeType msdElementTypeComplexShape
    Set ee = md.Scan(esc)
    best = 0
    Do While ee.MoveNext
        Set el = ee.Current
        If DC_LevelSo(el) = mLvBox Then
            On Error Resume Next
            Err.Clear
            rg = el.Range
            ax = rg.Low.x: ay = rg.Low.y
            bx = rg.High.x: by = rg.High.y
            If Err.Number = 0 Then
                a = (bx - ax) * (by - ay)
                If a > best Then
                    best = a: x1 = ax: y1 = ay: x2 = bx: y2 = by
                End If
            End If
            On Error GoTo 0
        End If
    Loop
    TimOSoDo = (best > 0)
End Function

Private Sub ThemPhanTu(ByVal el As Element, ByVal lvCha As Long)
    Dim lv As Long, subs As ElementEnumerator
    lv = DC_LevelSo(el)
    If lv <= 0 Then lv = lvCha
    On Error Resume Next

    If el.Type = msdElementTypeText Then
        ThemText el, lv
        Exit Sub
    End If
    If el.IsComplexElement Then
        Set subs = el.AsComplexElement.GetSubElements
        Do While subs.MoveNext
            ThemPhanTu subs.Current, lv
        Loop
        Exit Sub
    End If
    If el.IsVertexList Then ThemDuong el, lv
End Sub

Private Sub ThemDuong(ByVal el As Element, ByVal lv As Long)
    Dim pts() As Point3d, i As Long, s As String
    On Error Resume Next
    Err.Clear
    pts = el.AsVertexList.GetVertices
    If Err.Number <> 0 Then Exit Sub
    On Error GoTo 0
    For i = LBound(pts) To UBound(pts)
        If Not TrongCuaSo(pts(i).x, pts(i).y) Then Exit Sub
    Next i
    ' O so do trang Trich luc -> level 24 (modKhungMau tim o nay);
    ' phan tu khac tren level o so do (trang khac) -> doi level 25 cho khoi nham
    If lv = mLvBox Or lv = 24 Then
        If LaOSoDo(pts) Then lv = 24 Else lv = 25
    End If
    s = "L" & vbTab & lv
    For i = LBound(pts) To UBound(pts)
        s = s & vbTab & s2(pts(i).x * mS) & vbTab & s2(pts(i).y * mS)
        CapNhatBB pts(i).x * mS, pts(i).y * mS
    Next i
    ThemBuf s
    mNL = mNL + 1
End Sub

Private Function LaOSoDo(pts() As Point3d) As Boolean
    Dim i As Long, x1 As Double, y1 As Double, x2 As Double, y2 As Double, tol As Double
    x1 = pts(LBound(pts)).x: x2 = x1: y1 = pts(LBound(pts)).y: y2 = y1
    For i = LBound(pts) To UBound(pts)
        If pts(i).x < x1 Then x1 = pts(i).x
        If pts(i).x > x2 Then x2 = pts(i).x
        If pts(i).y < y1 Then y1 = pts(i).y
        If pts(i).y > y2 Then y2 = pts(i).y
    Next i
    tol = (mBx2 - mBx1) * 0.01
    LaOSoDo = (Abs(x1 - mBx1) < tol And Abs(x2 - mBx2) < tol And _
               Abs(y1 - mBy1) < tol And Abs(y2 - mBy2) < tol)
End Function

Private Sub ThemText(ByVal el As Element, ByVal lv As Long)
    Dim oT As TextElement, s As String, fn As String, h As Double
    Dim ox As Double, oy As Double, lx As Double, ly As Double, hy As Double
    Dim og As Point3d, rg As Range3d
    On Error Resume Next
    Set oT = el
    s = Trim$(oT.Text)
    If Len(s) = 0 Then Exit Sub
    fn = LCase$(oT.TextStyle.Font.Name)
    If Left$(fn, 2) = "vn" Or Left$(fn, 3) = ".vn" Then s = Tcvn3SangUnicode(s)
    s = ChuanTag(s)
    h = oT.TextStyle.Height
    og = oT.Origin: rg = el.Range
    ox = og.x: oy = og.y
    lx = rg.Low.x: ly = rg.Low.y: hy = rg.High.y
    On Error GoTo 0
    If h <= 0 Then h = hy - ly
    ' Diem dat chu = goc trai duoi (mau ve chu can le trai)
    If Abs(ox - lx) > h * 0.3 Then ox = lx
    If oy > ly + h * 0.6 Then oy = ly
    If Not TrongCuaSo(ox, oy) Then Exit Sub

    Dim kind As String
    If LaTag(s) Then kind = "TAG" Else kind = "TEXT"
    ' Tag bang toa do: luu TAM chu (modKhungMau dat chu can giua o)
    Select Case s
        Case "tttl", "tamXtl", "tamYtl", "cdtl"
            If hy > ly Then oy = (ly + hy) / 2#
        Case "tths", "cdhs", "tamxhs", "tamyhs", "ttkq", "cdkq", "tamxkq", "tamykq", "tt", "cd"
            ' bang phu (tt/cd: bang Doan-Chieu dai mau tach/hop thua): luu TAM chu ca X va Y
            If hy > ly Then oy = (ly + hy) / 2#
            If rg.High.x > lx Then ox = (lx + rg.High.x) / 2#
    End Select
    s = Replace(Replace(Replace(s, vbTab, " "), vbCr, " "), vbLf, " ")
    ThemBuf "T" & vbTab & lv & vbTab & kind & vbTab & s2(h * mS) & vbTab & _
            s2(ox * mS) & vbTab & s2(oy * mS) & vbTab & s
    CapNhatBB ox * mS, oy * mS
    mNT = mNT + 1
End Sub

' Placeholder dien gia tri (giu dung ten modKhungMau/GiaTriTag dang dung)
' SUA 15/10/2026: tag go sai hoa/thuong (tamxtl, tamytl...) hoac go thua
' chu (toBanDoo, tenXan) -> doi ve dung ten tag. Chu khac giu nguyen.
Private Function ChuanTag(ByVal s As String) As String
    Dim t As Variant, u As String
    ChuanTag = s
    u = LCase$(Trim$(s))
    If Len(u) = 0 Or Len(u) > 24 Then Exit Function
    If u = "tobandoo" Then ChuanTag = "toBanDo": Exit Function
    If u = "tenxan" Then ChuanTag = "tenXa": Exit Function
    For Each t In Array("soHieuThua", "toBanDo", "dienTich", "mdsd", "chuSuDung", "tenXa", "tenHuyen", "tenTinh", _
                        "gcn", "hinhThucSuDung", "diaChiChu", "diaChiThua", "tttl", "tamXtl", "tamYtl", "cdtl", _
                        "ttkq", "tamxkq", "tamykq", "cdkq", "tths", "tamxhs", "tamyhs", "cdhs")
        If u = LCase$(t) Then ChuanTag = t: Exit Function
    Next t
End Function

Private Function LaTag(ByVal s As String) As Boolean
    Select Case Trim$(s)
        Case "soHieuThua", "toBanDo", "dienTich", "mdsd", "chuSuDung", _
             "tenXa", "tenHuyen", "tenTinh", "gcn", "tinhhinhthaydoiranhgioi", _
             "hinhThucSuDung", "diaChiChu", "diaChiThua", _
             "tttl", "tamXtl", "tamYtl", "cdtl", _
             "ttkq", "tamxkq", "tamykq", "cdkq", "tths", "tamxhs", "tamyhs", "cdhs", "tt", "cd"
            LaTag = True      ' tag trang khac chua dien -> de trong
    End Select
End Function

Private Function TrongCuaSo(ByVal x As Double, ByVal y As Double) As Boolean
    TrongCuaSo = (x >= mWx1 And x <= mWx2 And y >= mWy1 And y <= mWy2)
End Function

Private Sub CapNhatBB(ByVal x As Double, ByVal y As Double)
    If Not mCoBB Then
        mMinX = x: mMaxX = x: mMinY = y: mMaxY = y: mCoBB = True
    Else
        If x < mMinX Then mMinX = x
        If x > mMaxX Then mMaxX = x
        If y < mMinY Then mMinY = y
        If y > mMaxY Then mMaxY = y
    End If
End Sub

'============================================================
' CHEP NGUYEN PHAN TU TU FILE MAU .dgn vao ban ve (giu font, can le,
' chi so tren, mau...) - giong gCadas. Bien doi: P' = P * sc + (tx, ty).
'   - Tag bang toa do (tttl, tamXtl...) : bo qua (modKhungMau tu dien)
'   - Tag thong tin (soHieuThua, dienTich...) : chep roi thay noi dung
'============================================================
Public Sub DC_ChepMauDgn(ByVal dgn As String, ByVal sc As Double, _
                         ByVal tX As Double, ByVal ty As Double, ByVal v As clsVung, _
                         ByVal toBanDo As String, ByVal tenXa As String, _
                         ByVal tenHuyen As String, ByVal tenTinh As String)
    Dim f As DesignFile, md As ModelReference
    Dim esc As ElementScanCriteria, ee As ElementEnumerator, el As Element, e2 As Element
    Dim tr As Transform3d, s As String, gt As String, laTagBang As Boolean

    On Error Resume Next
    Set f = Application.OpenDesignFileForProgram(dgn, True)
    On Error GoTo 0
    If f Is Nothing Then
        DC_ThongBao "Kh" & ChrW(244) & "ng m" & ChrW(7903) & " " & ChrW(273) & ChrW(432) & ChrW(7907) & "c file m" & ChrW(7851) & "u .dgn:" & vbCrLf & dgn, "Tr" & ChrW(237) & "ch l" & ChrW(7909) & "c", vbExclamation
        Exit Sub
    End If
    Set md = f.DefaultModelReference
    tr = Transform3dFromMatrix3dPoint3d(Matrix3dFromScale(sc), Point3dFromXYZ(tX, ty, 0#))

    Set esc = New ElementScanCriteria
    esc.ExcludeAllTypes
    esc.IncludeType msdElementTypeLine
    esc.IncludeType msdElementTypeLineString
    esc.IncludeType msdElementTypeShape
    esc.IncludeType msdElementTypeComplexString
    esc.IncludeType msdElementTypeComplexShape
    esc.IncludeType msdElementTypeText
    esc.IncludeType msdElementTypeTextNode
    esc.IncludeType msdElementTypeCellHeader
    esc.IncludeType msdElementTypeEllipse
    esc.IncludeType msdElementTypeArc
    ' SUA 11/10/2026: tach/hop thua - luot 1 ghi vi tri cac dong mo ta (3.4.k)
    Dim sTH As String, yTH As Double, boTH As Boolean
    If gTHCheDo > 0 Then
        TH_BatDauViTri
        Set ee = md.Scan(esc)
        Do While ee.MoveNext
            Set el = ee.Current
            If el.Type = msdElementTypeText Then
                sTH = "": yTH = 0
                On Error Resume Next
                sTH = Trim$(el.AsTextElement.Text)
                yTH = el.AsTextElement.Origin.y
                On Error GoTo 0
                If LaFontVn(el) Then sTH = Tcvn3SangUnicode(sTH)
                If Len(sTH) > 0 Then TH_GhiViTri sTH, yTH
            End If
        Loop
    End If

    ' SUA 22/10: tach/hop - dong "a) Thua so: | soHieuThua | , to ban do so: | toBanDo ..."
    '   (moi doan 1 chu rieng) -> gop thanh 1 chu lien, khong con ho giua cac doan
    Set mGop = Nothing
    If gTHCheDo > 0 Then GopDongMau md, esc, v, toBanDo, tenXa, tenHuyen, tenTinh
    Dim kGop As String
    Set ee = md.Scan(esc)
    Do While ee.MoveNext
        Set el = ee.Current
        gt = "": laTagBang = False
        If Not mGop Is Nothing Then
            kGop = ""
            On Error Resume Next
            kGop = DLongToString(el.id)
            On Error GoTo 0
            If mGop.Exists(kGop) Then
                If mGop(kGop) = Chr$(1) Then GoTo tiep
                If VeChuGop(el, CStr(mGop(kGop)), tr) Then GoTo tiep
            End If
        End If
        ' SUA 22/10: text node (chu 1 dong dang node) chua tag -> tach thanh chu don roi thay
        If el.Type = msdElementTypeTextNode Then
            If ChepNodeMau(el, tr, v, toBanDo, tenXa, tenHuyen, tenTinh) Then GoTo tiep
        End If
        If el.Type = msdElementTypeText Then
            s = ""
            On Error Resume Next
            s = Trim$(el.AsTextElement.Text)
            s = ChuanTag(s)
            On Error GoTo 0
            ' Tach/hop thua: thay chu mau theo thua (modTachHop)
            If gTHCheDo > 0 And Len(s) > 0 And Not LaTag(s) Then
                sTH = s
                If LaFontVn(el) Then sTH = Tcvn3SangUnicode(s)
                yTH = 0
                On Error Resume Next
                yTH = el.AsTextElement.Origin.y
                On Error GoTo 0
                gt = TH_ThayChu(sTH, yTH, boTH)
                If boTH Then GoTo tiep
                If gt <> sTH Then GoTo ChepPT
                gt = ""
            End If
            If LaTag(s) Then
                Select Case s
                    Case "tttl", "tamXtl", "tamYtl", "cdtl", "ttkq", "tamxkq", "tamykq", "cdkq", _
                         "tths", "tamxhs", "tamyhs", "cdhs", "tt", "cd"
                        laTagBang = True
                    Case Else
                        gt = GiaTri(s, v, toBanDo, tenXa, tenHuyen, tenTinh)
                        If Len(gt) = 0 Then laTagBang = True     ' khong co gia tri -> bo
                End Select
                If laTagBang Then GoTo tiep
            ElseIf Len(s) > 0 Then
                ' Chu mau (vd "ONT+CLN", "NGUYEN VAN A", dia chi mau) -> thay bang
                ' thong tin thua (bang thay the: ThayTheMau.txt)
                Dim su As String, khop As Boolean
                su = s
                If LaFontVn(el) Then su = Tcvn3SangUnicode(s)
                gt = ThayTheChuMau(su, v, toBanDo, tenXa, tenHuyen, tenTinh, khop)
                If khop And Len(gt) = 0 Then GoTo tiep
            End If
        End If

ChepPT:
        ' SUA 26/10: chu mau KHONG phai Times New Roman (.VnTime, Arial...) -> ve lai bang
        '   Times New Roman Unicode (may khong co font .Vn / Arial CE van hien dung)
        If el.Type = msdElementTypeText Then
            If ChuSangTNR(el, gt, tr) Then GoTo tiep
        End If
        Set e2 = Nothing
        On Error Resume Next
        Set e2 = ActiveModelReference.CopyElement(el)
        On Error GoTo 0
        If Not e2 Is Nothing Then
            On Error Resume Next
            ' SUA 22/10: phan tu mau bi KHOA (locked) -> Rewrite that bai, chu giu nguyen tag
            e2.IsLocked = False
            Err.Clear
            If Len(gt) > 0 Then
                If LaFontVn(e2) Then gt = UnicodeSangTcvn3(gt)
                e2.AsTextElement.Text = gt
                If DC_MauDien() >= 0 Then e2.color = DC_MauDien()
                ' SUA 22/10: chu co enter-data-field/linkage (mau TT26) -> doi Text khong an
                '   -> tao phan tu chu moi thay the
                If Err.Number <> 0 Or e2.AsTextElement.Text <> gt Then
                    Err.Clear
                    Set e2 = ChuMoiThay(el, e2, gt)
                End If
            End If
            e2.Transform tr
            If Not gLvHSMap Is Nothing Then
                If gLvHSMap.Exists(CStr(DC_LevelSo(el))) Then
                    DC_GanLevel e2, gLvHSMap(CStr(DC_LevelSo(el)))
                ElseIf Not gLvHSMot Is Nothing Then
                    DC_GanLevel e2, gLvHSMot
                End If
            ElseIf Not gLvHSMot Is Nothing Then
                DC_GanLevel e2, gLvHSMot
            End If
            ' Kieu net tuy bien (co do rong tuyet doi) khong co dan theo ty le
            ' -> mui ten huong Bac thanh vach day. Doi ve net lien 0.
            BoNetTuyBien e2
            Err.Clear
            e2.Rewrite
            If Err.Number <> 0 Then Err.Clear: ActiveModelReference.AddElement e2
            On Error GoTo 0
        End If
tiep:
    Loop
    f.Close
    ' SUA 22/10: tu day (so do, bang toa do, so lieu) ve bang mau dien them
    DC_DatMauDien
End Sub

' Mau chu dien them (-1 = tat)
Public Function DC_MauDien() As Long
    Dim s As String
    s = Trim$(DC_DocCauHinh("TL_MAUDIEN", "1"))
    If Len(s) = 0 Then s = "1"
    DC_MauDien = CLng(val(s))
    If DC_MauDien > 255 Then DC_MauDien = -1
End Function

Public Sub DC_DatMauDien()
    Dim m As Long
    m = DC_MauDien()
    If m < 0 Then Exit Sub
    On Error Resume Next
    If Not gDoiMauDien Then gMauDienCu = ActiveSettings.color
    ActiveSettings.color = m
    If Err.Number = 0 Then gDoiMauDien = True
    Err.Clear
End Sub

' Tra lai mau dang dung cua nguoi dung (goi sau khi ve xong trich luc / tach hop)
Public Sub DC_TraMauDien()
    If Not gDoiMauDien Then Exit Sub
    On Error Resume Next
    ActiveSettings.color = gMauDienCu
    gDoiMauDien = False
    Err.Clear
End Sub

' SUA 22/10: tao chu moi (cung symbology/kieu chu voi el), xoa ban sao cu
Private Function ChuMoiThay(ByVal el As Element, ByVal e2 As Element, ByVal gt As String) As Element
    Dim te As TextElement
    Set ChuMoiThay = e2
    On Error Resume Next
    Set te = CreateTextElement1(el, gt, el.AsTextElement.Origin, el.AsTextElement.Rotation)
    If te Is Nothing Then Err.Clear: Exit Function
    te.Level = el.Level: te.color = el.color
    te.IsLocked = False
    If DC_MauDien() >= 0 Then te.color = DC_MauDien()
    ActiveModelReference.RemoveElement e2
    Err.Clear
    Set ChuMoiThay = te
End Function

' SUA 22/10: text node trong mau (vd tag "soHieuThua" dat bang Place Text thanh node)
'   -> code cu chep nguyen node, khong thay tag. Neu co chu con can thay: ve tung
'   chu con thanh chu don (cung font/co/vi tri) roi bo node. Tra ve True = da xu ly.
Private Function ChepNodeMau(ByVal el As Element, tr As Transform3d, ByVal v As clsVung, _
                             ByVal toBanDo As String, ByVal tenXa As String, _
                             ByVal tenHuyen As String, ByVal tenTinh As String) As Boolean
    Dim ee As ElementEnumerator, c As Element, n As Long, i As Long, doi As Boolean
    Dim dS() As Element, kq() As String, bo() As Boolean
    Dim s As String, su As String, g As String, b As Boolean, khop As Boolean, y As Double
    On Error GoTo Thoi
    Set ee = el.AsTextNodeElement.GetSubElements
    ReDim dS(1 To 64): ReDim kq(1 To 64): ReDim bo(1 To 64)
    Do While ee.MoveNext
        Set c = ee.Current
        If c.IsTextElement And n < 64 Then
            n = n + 1: Set dS(n) = c
            s = ChuanTag(Trim$(c.AsTextElement.Text))
            su = s
            If LaFontVn(c) Then su = Tcvn3SangUnicode(s)
            kq(n) = su: g = su: b = False
            If Len(s) > 0 Then
                If LaTag(s) Then
                    Select Case s
                        Case "tttl", "tamXtl", "tamYtl", "cdtl", "ttkq", "tamxkq", "tamykq", "cdkq", _
                             "tths", "tamxhs", "tamyhs", "cdhs", "tt", "cd"
                            b = True
                        Case Else
                            g = GiaTri(s, v, toBanDo, tenXa, tenHuyen, tenTinh)
                            If Len(g) = 0 Then b = True
                    End Select
                ElseIf gTHCheDo > 0 Then
                    y = c.AsTextElement.Origin.y
                    g = TH_ThayChu(su, y, b)
                    If g = su And Not b Then
                        g = ThayTheChuMau(su, v, toBanDo, tenXa, tenHuyen, tenTinh, khop)
                        If khop And Len(g) = 0 Then b = True
                        If Len(g) = 0 Then g = su
                    End If
                Else
                    g = ThayTheChuMau(su, v, toBanDo, tenXa, tenHuyen, tenTinh, khop)
                    If khop And Len(g) = 0 Then b = True
                    If Len(g) = 0 Then g = su
                End If
            End If
            If b Then bo(n) = True: doi = True
            If g <> su And Not b Then kq(n) = g: doi = True
        End If
    Loop
    If Not doi Or n = 0 Then Exit Function

    Dim te As TextElement, gTX As String
    On Error Resume Next
    For i = 1 To n
        If Not bo(i) Then
            gTX = kq(i)
            If LaFontVn(dS(i)) Then gTX = UnicodeSangTcvn3(gTX)
            Set te = Nothing
            Set te = CreateTextElement1(dS(i), gTX, dS(i).AsTextElement.Origin, dS(i).AsTextElement.Rotation)
            If Not te Is Nothing Then
                te.Level = dS(i).Level: te.color = dS(i).color
                If kq(i) <> Trim$(dS(i).AsTextElement.Text) And DC_MauDien() >= 0 Then te.color = DC_MauDien()
                te.IsLocked = False
                te.Transform tr
                If Not gLvHSMap Is Nothing Then
                    If gLvHSMap.Exists(CStr(DC_LevelSo(el))) Then
                        DC_GanLevel te, gLvHSMap(CStr(DC_LevelSo(el)))
                    ElseIf Not gLvHSMot Is Nothing Then
                        DC_GanLevel te, gLvHSMot
                    End If
                ElseIf Not gLvHSMot Is Nothing Then
                    DC_GanLevel te, gLvHSMot
                End If
                Err.Clear
                ActiveModelReference.AddElement te
            End If
        End If
    Next i
    Err.Clear
    ChepNodeMau = True
    Exit Function
Thoi:
    ChepNodeMau = False
End Function

' SUA 22/10: chu con (text / node 1 dong) cua phan tu mau; Nothing neu khong phai
Private Function ChuCuaMau(ByVal el As Element) As Element
    Dim sb As ElementEnumerator, dem As Long, c As Element
    On Error GoTo Thoi
    If el.Type = msdElementTypeText Then Set ChuCuaMau = el: Exit Function
    If el.Type <> msdElementTypeTextNode Then Exit Function
    Set sb = el.AsTextNodeElement.GetSubElements
    Do While sb.MoveNext
        If sb.Current.IsTextElement Then dem = dem + 1: Set c = sb.Current
    Loop
    If dem = 1 Then Set ChuCuaMau = c
Thoi:
End Function

' Gia tri thay cho 1 chu mau (giong vong chinh). laDoi = co thay ; bo = bo chu
Private Function GiaTriChu(ByVal c As Element, ByVal v As clsVung, ByVal toBanDo As String, _
                           ByVal tenXa As String, ByVal tenHuyen As String, ByVal tenTinh As String, _
                           ByRef bo As Boolean, ByRef laDoi As Boolean) As String
    Dim raw As String, s As String, su As String, g As String, khop As Boolean
    bo = False: laDoi = False
    On Error Resume Next
    raw = c.AsTextElement.Text
    On Error GoTo 0
    If LaFontVn(c) Then raw = Tcvn3SangUnicode(raw)
    GiaTriChu = raw
    s = ChuanTag(Trim$(raw)): su = Trim$(raw)
    If Len(s) = 0 Then Exit Function
    If LaTag(s) Then
        Select Case s
            Case "tttl", "tamXtl", "tamYtl", "cdtl", "ttkq", "tamxkq", "tamykq", "cdkq", _
                 "tths", "tamxhs", "tamyhs", "cdhs", "tt", "cd"
                bo = True: Exit Function
        End Select
        g = GiaTri(s, v, toBanDo, tenXa, tenHuyen, tenTinh)
        laDoi = True
        If Len(g) = 0 Then bo = True
        GiaTriChu = g: Exit Function
    End If
    g = TH_ThayChu(su, c.AsTextElement.Origin.y, bo)
    If bo Then laDoi = True: Exit Function
    If g <> su Then laDoi = True: GiaTriChu = g: Exit Function
    g = ThayTheChuMau(su, v, toBanDo, tenXa, tenHuyen, tenTinh, khop)
    If khop Then
        laDoi = True
        If Len(g) = 0 Then bo = True Else GiaTriChu = g
    End If
End Function

' Tim cac dong chu lien nhau (cung level, cung hang, sat nhau) co it nhat 1 doan
' duoc thay -> ghi mGop: doan dau = chu gop, cac doan sau = Chr(1) (bo)
Private Sub GopDongMau(ByVal md As ModelReference, ByVal esc As ElementScanCriteria, ByVal v As clsVung, _
                       ByVal toBanDo As String, ByVal tenXa As String, _
                       ByVal tenHuyen As String, ByVal tenTinh As String)
    Const NMAX As Long = 3000
    Dim ee As ElementEnumerator, el As Element, c As Element, n As Long, i As Long, j As Long
    Dim ids() As String, x1() As Double, x2() As Double, yc() As Double, h() As Double
    Dim lv() As Long, gt() As String, doi() As Boolean, bo() As Boolean, Xong() As Boolean
    ReDim ids(1 To NMAX): ReDim x1(1 To NMAX): ReDim x2(1 To NMAX): ReDim yc(1 To NMAX)
    ReDim h(1 To NMAX): ReDim lv(1 To NMAX): ReDim gt(1 To NMAX)
    ReDim doi(1 To NMAX): ReDim bo(1 To NMAX): ReDim Xong(1 To NMAX)
    On Error GoTo Thoi
    Set ee = md.Scan(esc)
    Do While ee.MoveNext
        Set el = ee.Current
        Set c = ChuCuaMau(el)
        If Not c Is Nothing And n < NMAX Then
            n = n + 1
            ids(n) = DLongToString(el.id)
            x1(n) = el.Range.Low.x: x2(n) = el.Range.High.x
            yc(n) = (el.Range.Low.y + el.Range.High.y) / 2#
            h(n) = el.Range.High.y - el.Range.Low.y
            lv(n) = DC_LevelSo(el)
            gt(n) = GiaTriChu(c, v, toBanDo, tenXa, tenHuyen, tenTinh, bo(n), doi(n))
        End If
    Loop
    If n = 0 Then Exit Sub

    Dim hang() As Long, m As Long, a As Long, b As Long, tmp As Long, k As Long
    Dim dau As Long, cuoi As Long, s As String, p As String, coDoi As Boolean
    ReDim hang(1 To n)
    For i = 1 To n
        If doi(i) And Not Xong(i) And h(i) > 0# Then
            ' cac chu cung hang voi i
            m = 0
            For j = 1 To n
                If lv(j) = lv(i) And Abs(yc(j) - yc(i)) < h(i) * 0.4 Then m = m + 1: hang(m) = j
            Next j
            ' sap theo x
            For a = 1 To m - 1
                For b = a + 1 To m
                    If x1(hang(b)) < x1(hang(a)) Then tmp = hang(a): hang(a) = hang(b): hang(b) = tmp
                Next b
            Next a
            ' doan lien chua i (khe < 1.5 chieu cao chu)
            For k = 1 To m
                If hang(k) = i Then Exit For
            Next k
            dau = k: cuoi = k
            Do While dau > 1
                If x1(hang(dau)) - x2(hang(dau - 1)) > h(i) * 1.5 Then Exit Do
                dau = dau - 1
            Loop
            Do While cuoi < m
                If x1(hang(cuoi + 1)) - x2(hang(cuoi)) > h(i) * 1.5 Then Exit Do
                cuoi = cuoi + 1
            Loop
            If cuoi > dau Then
                s = ""
                For k = dau To cuoi
                    Xong(hang(k)) = True
                    If Not bo(hang(k)) Then
                        p = gt(hang(k))
                        If Len(s) > 0 And Len(p) > 0 Then
                            If Right$(s, 1) <> " " And Left$(p, 1) <> " " And Left$(p, 1) <> "," Then
                                If Right$(s, 1) = ":" Or Right$(s, 1) = "," Then s = s & " "
                            End If
                        End If
                        s = s & p
                    End If
                Next k
                If mGop Is Nothing Then Set mGop = CreateObject("Scripting.Dictionary")
                For k = dau To cuoi
                    mGop(ids(hang(k))) = Chr$(1)
                Next k
                If Len(Trim$(s)) > 0 Then mGop(ids(hang(dau))) = s
            End If
        End If
    Next i
    Exit Sub
Thoi:
    Set mGop = Nothing
End Sub

' Ve chu gop tai vi tri doan dau (cung font/co/mau cua doan dau)
Private Function VeChuGop(ByVal el As Element, ByVal s As String, tr As Transform3d) As Boolean
    Dim c As Element, te As TextElement
    On Error GoTo Thoi
    Set c = ChuCuaMau(el)
    If c Is Nothing Then Exit Function
    If LaFontVn(c) Then s = UnicodeSangTcvn3(s)
    On Error Resume Next
    Set te = CreateTextElement1(c, s, c.AsTextElement.Origin, c.AsTextElement.Rotation)
    If te Is Nothing Then Exit Function
    te.Level = c.Level: te.color = c.color
    te.IsLocked = False
    If DC_MauDien() >= 0 Then te.color = DC_MauDien()
    te.Transform tr
    If Not gLvHSMap Is Nothing Then
        If gLvHSMap.Exists(CStr(DC_LevelSo(el))) Then
            DC_GanLevel te, gLvHSMap(CStr(DC_LevelSo(el)))
        ElseIf Not gLvHSMot Is Nothing Then
            DC_GanLevel te, gLvHSMot
        End If
    ElseIf Not gLvHSMot Is Nothing Then
        DC_GanLevel te, gLvHSMot
    End If
    Err.Clear
    ActiveModelReference.AddElement te
    VeChuGop = (Err.Number = 0)
    Err.Clear
    Exit Function
Thoi:
    VeChuGop = False
End Function

' SUA 26/10: tao lai chu mau bang font Times New Roman (Unicode). gt = chu da thay (Unicode)
'   hoac "" (giu noi dung mau). Tra ve True neu da ve thay (bo ban chep goc).
Private Function ChuSangTNR(ByVal el As Element, ByVal gt As String, tr As Transform3d) As Boolean
    Dim fn As String, s As String, i As Long, c As Long, kq As String
    Dim h As Double, w As Double, j As Long, te As TextElement, f As Object
    On Error Resume Next
    fn = el.AsTextElement.TextStyle.Font.Name
    If Err.Number <> 0 Then Err.Clear: Exit Function
    If StrComp(fn, "Times New Roman", vbTextCompare) = 0 Then Exit Function
    If Len(gt) > 0 Then
        s = gt
    Else
        s = el.AsTextElement.Text
        If LaFontVn(el) Then s = Tcvn3SangUnicode(s)
    End If
    For i = 1 To Len(s)                       ' bo ky tu dieu khien (vd Chr(16) trong mau .VnTime)
        c = AscW(Mid$(s, i, 1))
        If c >= 32 Or c < 0 Then kq = kq & Mid$(s, i, 1)
    Next i
    If Len(Trim$(kq)) = 0 Then Exit Function
    Set f = ActiveDesignFile.Fonts.Find(msdFontTypeWindowsTrueType, "Times New Roman")
    If f Is Nothing Then Err.Clear: Exit Function
    h = el.AsTextElement.TextStyle.Height
    w = el.AsTextElement.TextStyle.Width
    j = el.AsTextElement.TextStyle.Justification
    If Err.Number <> 0 Or h <= 0 Then Err.Clear: Exit Function
    Set ActiveSettings.TextStyle.Font = f
    ActiveSettings.TextStyle.Height = h
    ActiveSettings.TextStyle.Width = w
    ActiveSettings.TextStyle.Justification = j
    Err.Clear
    Set te = CreateTextElement1(Nothing, kq, el.AsTextElement.Origin, el.AsTextElement.Rotation)
    If te Is Nothing Or Err.Number <> 0 Then Err.Clear: Exit Function
    Set te.Level = el.Level
    te.color = el.color
    te.LineWeight = 0
    If Len(gt) > 0 And DC_MauDien() >= 0 Then te.color = DC_MauDien()
    te.Transform tr
    If Not gLvHSMap Is Nothing Then
        If gLvHSMap.Exists(CStr(DC_LevelSo(el))) Then
            DC_GanLevel te, gLvHSMap(CStr(DC_LevelSo(el)))
        ElseIf Not gLvHSMot Is Nothing Then
            DC_GanLevel te, gLvHSMot
        End If
    ElseIf Not gLvHSMot Is Nothing Then
        DC_GanLevel te, gLvHSMot
    End If
    Err.Clear
    ActiveModelReference.AddElement te
    ChuSangTNR = (Err.Number = 0)
    Err.Clear
End Function

Private Sub BoNetTuyBien(ByVal e As Element)
    Dim ten As String, ls As LineStyle
    On Error Resume Next
    If e.IsTextElement Then Exit Sub
    ten = e.LineStyle.Name
    If Err.Number <> 0 Then Err.Clear: Exit Sub
    If Len(ten) = 1 And ten >= "0" And ten <= "7" Then Exit Sub
    Set ls = ActiveDesignFile.LineStyles.Find("0")
    If ls Is Nothing Then Set ls = ActiveDesignFile.LineStyles(1)
    If Not ls Is Nothing Then
        Set e.LineStyle = ls
        If Err.Number <> 0 Then Err.Clear: e.LineStyle = ls
    End If
    Err.Clear
End Sub

'============================================================
' Hop thoai LUU file (Windows) - tra ve duong dan, rong = huy
'============================================================
Public Function DC_LuuFile(ByVal loc As String, ByVal tieuDe As String, _
                           ByVal tenMacDinh As String, ByVal duoi As String) As String
    Dim o As OPENFILENAME, r As Long, p As Long, ten As String
    o.lStructSize = Len(o)
    o.lpstrFilter = Replace(loc, "|", vbNullChar) & vbNullChar & vbNullChar
    ten = tenMacDinh
    p = InStrRev(ten, "\")
    If p > 0 Then o.lpstrInitialDir = Left$(ten, p - 1): ten = Mid$(ten, p + 1)
    o.lpstrFile = ten & String$(1024 - Len(ten), vbNullChar)
    o.nMaxFile = 1024
    o.lpstrTitle = tieuDe
    o.lpstrDefExt = duoi
    o.flags = &H2 Or &H800 Or &H4                ' OVERWRITEPROMPT, PATHMUSTEXIST, HIDEREADONLY
    r = GetSaveFileNameA(o)
    If r <> 0 Then
        p = InStr(o.lpstrFile, vbNullChar)
        If p > 0 Then DC_LuuFile = Left$(o.lpstrFile, p - 1) Else DC_LuuFile = o.lpstrFile
    End If
End Function

'--- Gan level cho phan tu (ca phan tu con cua cell / phan tu phuc)
Public Sub DC_GanLevel(ByVal e As Element, ByVal lv As Level)
    On Error Resume Next
    Set e.Level = lv
    If Err.Number <> 0 Then Err.Clear: e.Level = lv
    Err.Clear
End Sub

' Bang thay the chu mau: C:\DiaChinhVL\Mau\ThayTheMau.txt (UTF-8), moi dong:
'     <chu mau dung y nguyen trong file mau>|<truong>
'   truong: soHieuThua, toBanDo, dienTich, mdsd, chuSuDung, diaChiChu,
'           tenXa, tenHuyen, tenTinh, diaChiThua (xa, huyen, tinh)
' Khong co file -> dung bang mac dinh (mau tluc.dgn kieu gCadas).
Private Function ThayTheChuMau(ByVal s As String, ByVal v As clsVung, ByVal toBanDo As String, _
                               ByVal tenXa As String, ByVal tenHuyen As String, _
                               ByVal tenTinh As String, ByRef khop As Boolean) As String
    Dim dS As Variant, i As Long, p As Long, mau As String, tr As String
    khop = False
    dS = DsThayThe()
    For i = 0 To UBound(dS)
        p = InStrRev(dS(i), "|")
        If p > 1 Then
            mau = Trim$(Left$(dS(i), p - 1)): tr = Trim$(Mid$(dS(i), p + 1))
            If StrComp(Trim$(s), mau, vbBinaryCompare) = 0 Then
                khop = True
                ThayTheChuMau = GiaTri(tr, v, toBanDo, tenXa, tenHuyen, tenTinh)
                Exit Function
            End If
        End If
    Next i
End Function

Private Function DsThayThe() As Variant
    Dim f As String, st As Object, t As String
    f = DC_THUMUC & "\Mau\ThayTheMau.txt"
    If Len(Dir$(f)) > 0 Then
        On Error Resume Next
        Set st = CreateObject("ADODB.Stream")
        st.Type = 2: st.Charset = "utf-8": st.Open
        st.LoadFromFile f
        t = st.ReadText
        st.Close
        On Error GoTo 0
        t = Replace(t, vbCr, "")
        If Left$(t, 1) = ChrW(&HFEFF) Then t = Mid$(t, 2)
        If Len(Trim$(t)) > 0 Then DsThayThe = Split(t, vbLf): Exit Function
    End If
    DsThayThe = Array("ONT+CLN|mdsd", _
                      "NGUY" & ChrW(7876) & "N V" & ChrW(258) & "N A|chuSuDung", _
                      ChrW(7845) & "p Dinh An, x" & ChrW(227) & " Phong Th" & ChrW(7841) & "nh An Ph" & ChrW(250) & " T" & ChrW(226) & "n, t" & ChrW(7881) & "nh V" & ChrW(297) & "nh Long|diaChiThua")
End Function

' "Xa An Phu Tan" -> "xa An Phu Tan" (chu dau viet thuong, dung giua cau)
Private Function ThuongDau(ByVal s As String) As String
    s = Trim$(s)
    If Len(s) > 0 Then ThuongDau = LCase$(Left$(s, 1)) & Mid$(s, 2)
End Function

Private Function GiaTri(ByVal tag As String, ByVal v As clsVung, ByVal toBanDo As String, _
                        ByVal tenXa As String, ByVal tenHuyen As String, ByVal tenTinh As String) As String
    Select Case tag
        Case "soHieuThua": GiaTri = v.soThua
        Case "toBanDo":    GiaTri = toBanDo
        Case "dienTich":   GiaTri = Replace(Format$(Round(v.dt, 1), "0.0"), ".", ",")
        Case "mdsd":       GiaTri = v.loaiDat
        Case "chuSuDung":  GiaTri = v.TenChu
        Case "diaChiChu":  GiaTri = v.DiaChi
        Case "tenXa":      GiaTri = tenXa
        Case "tenHuyen":   GiaTri = tenHuyen
        Case "tenTinh":    GiaTri = tenTinh
        Case "diaChiThua"
            Dim dc As String
            If Len(Trim$(tenXa)) > 0 Then dc = ThuongDau(tenXa)
            If Len(Trim$(tenHuyen)) > 0 Then dc = dc & IIf(Len(dc) > 0, ", ", "") & ThuongDau(tenHuyen)
            If Len(Trim$(tenTinh)) > 0 Then dc = dc & IIf(Len(dc) > 0, ", ", "") & ThuongDau(tenTinh)
            GiaTri = dc
    End Select
End Function

Private Function LaFontVn(ByVal e As Element) As Boolean
    Dim fn As String
    On Error Resume Next
    fn = LCase$(e.AsTextElement.TextStyle.Font.Name)
    LaFontVn = (Left$(fn, 2) = "vn" Or Left$(fn, 3) = ".vn")
End Function

' Unicode -> TCVN3 (khi o mau dung font VnTime)
Private Function UnicodeSangTcvn3(ByVal s As String) As String
    Dim i As Long, j As Long, c As Long, r As String, gap As Boolean
    NapTcvn
    For i = 1 To Len(s)
        c = AscW(Mid$(s, i, 1)) And &HFFFF&
        gap = False
        If c >= 128 Then
            For j = 161 To 255
                If mTcvn(j) = c Then r = r & ChrW(j): gap = True: Exit For
            Next j
        End If
        If Not gap Then r = r & ChrW(c)
    Next i
    UnicodeSangTcvn3 = r
End Function

' Dung chung (modTienIch: doi font chu ban ve)
Public Function DC_Tcvn3SangUnicode(ByVal s As String) As String
    DC_Tcvn3SangUnicode = Tcvn3SangUnicode(s)
End Function

'------------------------------------------------------------ TCVN3 -> Unicode
Private Function Tcvn3SangUnicode(ByVal s As String) As String
    Dim i As Long, c As Long, b As Long, r As String
    NapTcvn
    For i = 1 To Len(s)
        c = AscW(Mid$(s, i, 1)) And &HFFFF&
        b = ByteGoc(c)
        If b >= 0 And b <= 255 Then
            If mTcvn(b) <> 0 Then r = r & ChrW(mTcvn(b)) Else r = r & ChrW(c)
        Else
            r = r & ChrW(c)
        End If
    Next i
    Tcvn3SangUnicode = r
End Function

' Ma byte goc cua ky tu (may dung bang ma 1252 hoac 1258)
Private Function ByteGoc(ByVal c As Long) As Long
    If c < 256 Then ByteGoc = c: Exit Function
    Select Case c
        Case &H102: ByteGoc = &HC3
        Case &H300: ByteGoc = &HCC
        Case &H309: ByteGoc = &HD2
        Case &H1AF: ByteGoc = &HDD
        Case &H303: ByteGoc = &HDE
        Case &H103: ByteGoc = &HE3
        Case &H301: ByteGoc = &HEC
        Case &H323: ByteGoc = &HF2
        Case &H1B0: ByteGoc = &HFD
        Case &H20AB: ByteGoc = &HFE
        Case Else: ByteGoc = -1
    End Select
End Function

Private Sub NapTcvn()
    Dim a() As String, i As Long
    If mTcvnNap Then Exit Sub
    a = Split(TCVN_MAP, ",")
    For i = LBound(a) To UBound(a)
        mTcvn(CLng("&H" & Left$(a(i), 2))) = CLng("&H" & Mid$(a(i), 3, 4))
    Next i
    mTcvnNap = True
End Sub

'------------------------------------------------------------ INI kieu gCadas
Private Function DocIni(ByVal path As String, ByVal sec As String, _
                        ByVal khoa As String, ByVal macDinh As String) As String
    Dim n As Integer, ln As String, trongSec As Boolean, p As Long
    DocIni = macDinh
    If Len(path) = 0 Then Exit Function
    If Len(Dir$(path)) = 0 Then Exit Function
    On Error GoTo Xong
    n = FreeFile
    Open path For Input As #n
    Do While Not EOF(n)
        Line Input #n, ln
        ln = Trim$(ln)
        If Left$(ln, 1) = "[" Then
            trongSec = (StrComp(ln, "[" & sec & "]", vbTextCompare) = 0)
        ElseIf trongSec Then
            p = InStr(ln, "=")
            If p > 1 Then
                If StrComp(Trim$(Left$(ln, p - 1)), khoa, vbTextCompare) = 0 Then
                    DocIni = Trim$(Mid$(ln, p + 1))
                    Exit Do
                End If
            End If
        End If
    Loop
Xong:
    On Error Resume Next
    Close #n
End Function

Private Function SoLevel(ByVal s As String, ByVal macDinh As Long) As Long
    Dim t As String
    t = Trim$(s)
    If LCase$(Left$(t, 6)) = "level " Then t = Trim$(Mid$(t, 7))
    If IsNumeric(t) Then SoLevel = CLng(val(t)) Else SoLevel = macDinh
End Function

'------------------------------------------------------------ tien ich
Private Function s2(ByVal v As Double) As String
    s2 = Trim$(Str$(v))
End Function

Private Sub ThemBuf(ByVal s As String)
    If mN > UBound(mBuf) Then ReDim Preserve mBuf(0 To UBound(mBuf) * 2 + 1)
    mBuf(mN) = s
    mN = mN + 1
End Sub

Private Function JoinBuf() As String
    Dim r() As String, i As Long
    If mN = 0 Then Exit Function
    ReDim r(0 To mN - 1)
    For i = 0 To mN - 1: r(i) = mBuf(i): Next i
    JoinBuf = Join(r, vbLf) & vbLf
End Function

Private Function GhiUtf8(ByVal path As String, ByVal txt As String) As Boolean
    Dim st As Object
    On Error Resume Next
    Set st = CreateObject("ADODB.Stream")
    st.Type = 2: st.Charset = "utf-8": st.Open
    st.WriteText txt
    st.SaveToFile path, 2
    st.Close
    If Err.Number <> 0 Then
        DC_ThongBao "Kh" & ChrW(244) & "ng ghi " & ChrW(273) & ChrW(432) & ChrW(7907) & "c file m" & ChrW(7851) & "u: " & path & vbCrLf & Err.Description, "B" & ChrW(7855) & "t m" & ChrW(7851) & "u", vbExclamation
        Exit Function
    End If
    GhiUtf8 = True
End Function

Attribute VB_Name = "modMenuDC"
'============================================================
' modMenuDC - Thanh menu kieu LandMap cho DiaChinhVL
'   - Popup menu that cua Windows (AppendMenuW -> giu chu Viet Unicode)
'   - TrackPopupMenu + TPM_RETURNCMD: khong can subclass, an toan
'
' THEM CONG CU MOI (2 buoc):
'   1. Trong TaoMenu: them dong  Muc h, "<ten hien thi>", "<MA>"
'      (MA = "" -> muc mo xam, chua dung duoc)
'   2. Trong DC_ChayLenh: them  Case "<MA>": <ten Sub can goi>
'============================================================
Option Explicit

Private Type POINTAPI
    x As Long
    y As Long
End Type

Private Declare Function CreatePopupMenu Lib "user32" () As Long
Private Declare Function AppendMenuW Lib "user32" (ByVal hMenu As Long, ByVal uFlags As Long, ByVal uIDNewItem As Long, ByVal lpNewItem As Long) As Long
Private Declare Function TrackPopupMenu Lib "user32" (ByVal hMenu As Long, ByVal uFlags As Long, ByVal x As Long, ByVal y As Long, ByVal nReserved As Long, ByVal hwnd As Long, ByVal prcRect As Long) As Long
Private Declare Function DestroyMenu Lib "user32" (ByVal hMenu As Long) As Long
Private Declare Function GetCursorPos Lib "user32" (lpPoint As POINTAPI) As Long
Private Declare Function FindWindowA Lib "user32" (ByVal lpClassName As String, ByVal lpWindowName As String) As Long
Private Declare Function GetForegroundWindow Lib "user32" () As Long
Private Declare Function SetForegroundWindow Lib "user32" (ByVal hwnd As Long) As Long
Private Declare Function GetDC Lib "user32" (ByVal hwnd As Long) As Long
Private Declare Function ReleaseDC Lib "user32" (ByVal hwnd As Long, ByVal hdc As Long) As Long
Private Declare Function GetDeviceCaps Lib "gdi32" (ByVal hdc As Long, ByVal nIndex As Long) As Long
Private Declare Function LoadImageA Lib "user32" (ByVal hInst As Long, ByVal lpszName As String, ByVal uType As Long, ByVal cxDesired As Long, ByVal cyDesired As Long, ByVal fuLoad As Long) As Long
Private Declare Function SendMessageA Lib "user32" (ByVal hwnd As Long, ByVal wMsg As Long, ByVal wParam As Long, ByVal lParam As Long) As Long
Private Declare Function GetWindowLongA Lib "user32" (ByVal hwnd As Long, ByVal nIndex As Long) As Long
Private Declare Function SetWindowLongA Lib "user32" (ByVal hwnd As Long, ByVal nIndex As Long, ByVal dwNewLong As Long) As Long
Private Declare Function SetWindowPos Lib "user32" (ByVal hwnd As Long, ByVal hWndInsertAfter As Long, ByVal x As Long, ByVal y As Long, ByVal cx As Long, ByVal cy As Long, ByVal wFlags As Long) As Long
Private Declare Function MessageBoxW Lib "user32" (ByVal hwnd As Long, ByVal lpText As Long, ByVal lpCaption As Long, ByVal uType As Long) As Long

Private Const MF_STRING As Long = &H0
Private Const MF_GRAYED As Long = &H1
Private Const MF_SEPARATOR As Long = &H800
Private Const MF_POPUP As Long = &H10
Private Const MF_CHECKED As Long = &H8
Private Const TPM_LEFTBUTTON As Long = &H0
Private Const TPM_NONOTIFY As Long = &H80
Private Const TPM_RETURNCMD As Long = &H100
Private Const LOGPIXELSX As Long = 88

Private Const IMAGE_ICON As Long = 1
Private Const LR_LOADFROMFILE As Long = &H10
Private Const WM_SETICON As Long = &H80
Private Const ICON_SMALL As Long = 0
Private Const ICON_BIG As Long = 1
Private Const GWL_EXSTYLE As Long = -20
Private Const WS_EX_DLGMODALFRAME As Long = &H1
Private Const SWP_FLAGS As Long = &H27      ' NOSIZE Or NOMOVE Or NOZORDER Or FRAMECHANGED

Public Const DC_THUMUC As String = "C:\DiaChinhVL"
Public Const DC_ICON As String = "C:\DiaChinhVL\DiaChinhVL.ico"

Private mMa() As String     ' id menu -> ma lenh
Private mN As Long

'============================================================
' NOI DUNG CAC MENU  (sua o day khi them cong cu)
'============================================================
Private Function TaoMenu(ByVal ten As String) As Long
    Dim h As Long
    h = CreatePopupMenu()
    If h = 0 Then Exit Function
    mN = 0
    ReDim mMa(1 To 1)

    Select Case ten
    Case "HETHONG"
        Muc h, "Thi" & ChrW(7871) & "t l" & ChrW(7853) & "p " & ChrW(273) & ChrW(417) & "n v" & ChrW(7883) & " h" & ChrW(224) & "nh ch" & ChrW(237) & "nh...", "DONVIHC"
        Gach h
        Muc h, "Thi" & ChrW(7871) & "t l" & ChrW(7853) & "p m" & ChrW(7863) & "c " & ChrW(273) & ChrW(7883) & "nh (n" & ChrW(233) & "t 0, font Times New Roman)", "MACDINH"
        Muc h, "M" & ChrW(7903) & " th" & ChrW(432) & " m" & ChrW(7909) & "c d" & ChrW(7919) & " li" & ChrW(7879) & "u (C:\DiaChinhVL)", "THUMUC"
        Gach h
        Muc h, ChrW(272) & ChrW(243) & "ng menu " & ChrW(272) & ChrW(7883) & "a Ch" & ChrW(237) & "nh VL", "DONG"

    Case "BANDO"
        Dim hd As Long, hT As Long
        hd = MenuCon(h, "X" & ChrW(7917) & " l" & ChrW(253) & " s" & ChrW(7889) & " li" & ChrW(7879) & "u tr" & ChrW(7883) & " " & ChrW(273) & "o")
        Muc hd, "N" & ChrW(7889) & "i ranh th" & ChrW(7917) & "a theo tr" & ChrW(7883) & " " & ChrW(273) & "o", ""
        Gach hd
        Muc hd, "Hi" & ChrW(7875) & "n th" & ChrW(7883) & " tr" & ChrW(7883) & " " & ChrW(273) & "o t" & ChrW(7885) & "a " & ChrW(273) & ChrW(7897), "TDTOADO"
        Muc hd, "Hi" & ChrW(7875) & "n th" & ChrW(7883) & " tr" & ChrW(7883) & " " & ChrW(273) & "o g" & ChrW(243) & "c c" & ChrW(7841) & "nh", "TDGOCCANH"
        Gach hd
        Muc hd, "Tri" & ChrW(7875) & "n " & ChrW(273) & "i" & ChrW(7875) & "m theo h" & ChrW(7891) & " s" & ChrW(417), ""
        Muc hd, "Tri" & ChrW(7875) & "n " & ChrW(273) & "i" & ChrW(7875) & "m theo danh s" & ChrW(225) & "ch", "TRIENDS"
        Gach hd
        Muc hd, "Giao h" & ChrW(7897) & "i thu" & ChrW(7853) & "n " & ChrW(273) & "i" & ChrW(7875) & "m mia", ""
        Muc hd, "Giao h" & ChrW(7897) & "i ngh" & ChrW(7883) & "ch " & ChrW(273) & "i" & ChrW(7875) & "m mia", ""
        hT = MenuCon(h, "T" & ChrW(7841) & "o Topology th" & ChrW(7917) & "a " & ChrW(273) & ChrW(7845) & "t")
        Muc hT, "T" & ChrW(7921) & " " & ChrW(273) & ChrW(7897) & "ng t" & ChrW(236) & "m, s" & ChrW(7917) & "a l" & ChrW(7895) & "i", "TIMLOI"
        Muc hT, "S" & ChrW(7917) & "a l" & ChrW(7895) & "i ranh th" & ChrW(7911) & " c" & ChrW(244) & "ng", ""
        Muc hT, "T" & ChrW(236) & "m c" & ChrW(7841) & "nh th" & ChrW(7917) & "a qu" & ChrW(225) & " ng" & ChrW(7855) & "n", "CANHNGAN"
        Muc hT, "L" & ChrW(224) & "m tr" & ChrW(242) & "n s" & ChrW(7889) & " l" & ChrW(7867) & " t" & ChrW(7885) & "a " & ChrW(273) & ChrW(7897), "LAMTRON"
        Muc hT, "T" & ChrW(236) & "m g" & ChrW(243) & "c nh" & ChrW(7887) & ", " & ChrW(273) & "i" & ChrW(7875) & "m th" & ChrW(7859) & "ng h" & ChrW(224) & "ng", "GOCNHO"
        Gach hT
        Muc hT, "X" & ChrW(243) & "a Topology th" & ChrW(7917) & "a " & ChrW(273) & ChrW(7845) & "t", ""
        Muc hT, "T" & ChrW(7841) & "o Topology th" & ChrW(7917) & "a " & ChrW(273) & ChrW(7845) & "t", "TOPO"
        Gach h
        Muc h, "T" & ChrW(7841) & "o Topology / CSDL", "TOPO"
        Muc h, "T" & ChrW(236) & "m l" & ChrW(7895) & "i", "TIMLOI"
        Gach h
        Muc h, "G" & ChrW(225) & "n th" & ChrW(244) & "ng tin", "GANTT"
        Muc h, "B" & ChrW(7843) & "ng d" & ChrW(7919) & " li" & ChrW(7879) & "u", "BANGDL"
        Muc h, "V" & ChrW(7869) & " nh" & ChrW(227) & "n th" & ChrW(7917) & "a...", "VENHAN"     ' SUA 25/10

    Case "BIENTAP"
        Dim hS As Long, tL As Variant, tlCu As Long, hQ As Long
        hS = MenuCon(h, "T" & ChrW(7927) & " l" & ChrW(7879) & " b" & ChrW(7843) & "n " & ChrW(273) & ChrW(7891))
        tlCu = DC_TyLeBD()
        For Each tL In Array(200, 500, 1000, 2000, 5000, 10000)
            MucTick hS, "T" & ChrW(7927) & " l" & ChrW(7879) & " b" & ChrW(7843) & "n " & ChrW(273) & ChrW(7891) & " 1:" & tL, "TY:" & tL, (CLng(tL) = tlCu)
        Next tL
        Gach h
        NhomBT h, "THUA", "Th" & ChrW(7917) & "a " & ChrW(273) & ChrW(7845) & "t"
        NhomBT h, "NHA", "Nh" & ChrW(224)
        NhomBT h, "GT", "Giao th" & ChrW(244) & "ng"
        NhomBT h, "TV", "Th" & ChrW(7911) & "y h" & ChrW(7879)
        NhomBT h, "DG", ChrW(272) & ChrW(7883) & "a gi" & ChrW(7899) & "i"
        hQ = MenuCon(h, "Quy ho" & ChrW(7841) & "ch"): Muc hQ, "(s" & ChrW(7855) & "p c" & ChrW(243) & ")", ""
        hQ = MenuCon(h, "K" & ChrW(253) & " hi" & ChrW(7879) & "u"): Muc hQ, "(s" & ChrW(7855) & "p c" & ChrW(243) & ")", ""
        hQ = MenuCon(h, "T" & ChrW(234) & "n ri" & ChrW(234) & "ng"): Muc hQ, "(s" & ChrW(7855) & "p c" & ChrW(243) & ")", ""
        Gach h
        Muc h, "Thanh c" & ChrW(244) & "ng c" & ChrW(7909), ""
        Muc h, "Ghi ch" & ChrW(250) & " t" & ChrW(7855) & "t", ""
        Muc h, "Quy " & ChrW(273) & ChrW(7883) & "nh l" & ChrW(7899) & "p (level, m" & ChrW(224) & "u, n" & ChrW(233) & "t, c" & ChrW(7905) & " ch" & ChrW(7919) & ")...", "QDLOP"
        Muc h, "B" & ChrW(7897) & " bi" & ChrW(234) & "n t" & ChrW(7853) & "p", ""
        Gach h
        Muc h, "G" & ChrW(225) & "n nh" & ChrW(227) & "n th" & ChrW(7917) & "a", "GANNHAN"
        Gach h
        Muc h, "T" & ChrW(244) & " m" & ChrW(224) & "u theo lo" & ChrW(7841) & "i " & ChrW(273) & ChrW(7845) & "t", ""
        Muc h, "Chia " & ChrW(273) & "o" & ChrW(7841) & "n t" & ChrW(7841) & "i giao " & ChrW(273) & "i" & ChrW(7875) & "m (c" & ChrW(7855) & "t n" & ChrW(233) & "t ranh)", "CHIADOAN"


    Case "KIEMKE"
        ' SUA 16/10/2026: menu Kiem ke chi tiet kieu LandMap; muc chua lam = mo
        Dim hK As Long, hK2 As Long, kkMau As String
        hK = MenuCon(h, "C" & ChrW(244) & "ng c" & ChrW(7909) & " h" & ChrW(7895) & " tr" & ChrW(7907) & " bi" & ChrW(234) & "n t" & ChrW(7853) & "p")
        hK2 = MenuCon(hK, ChrW(272) & ChrW(7863) & "t t" & ChrW(7927) & " l" & ChrW(7879))
        tlCu = DC_TyLeBD()
        For Each tL In Array(200, 500, 1000, 2000, 5000, 10000, 25000, 50000)
            MucTick hK2, "T" & ChrW(7927) & " l" & ChrW(7879) & " b" & ChrW(7843) & "n " & ChrW(273) & ChrW(7891) & " 1:" & tL, "TY:" & tL, (CLng(tL) = tlCu)
        Next tL
        hK2 = MenuCon(hK, "Tr" & ChrW(236) & "nh b" & ChrW(224) & "y"): Muc hK2, "(s" & ChrW(7855) & "p c" & ChrW(243) & ")", ""
        hK2 = MenuCon(hK, "K" & ChrW(253) & " hi" & ChrW(7879) & "u"): Muc hK2, "(s" & ChrW(7855) & "p c" & ChrW(243) & ")", ""
        NhomBT hK, "DG", ChrW(272) & ChrW(7883) & "a gi" & ChrW(7899) & "i"
        NhomBT hK, "GT", "Giao th" & ChrW(244) & "ng"
        NhomBT hK, "TV", "Th" & ChrW(7911) & "y h" & ChrW(7879)
        hK2 = MenuCon(hK, ChrW(272) & ChrW(7883) & "a h" & ChrW(236) & "nh"): Muc hK2, "(s" & ChrW(7855) & "p c" & ChrW(243) & ")", ""
        hK2 = MenuCon(hK, "Khoanh " & ChrW(273) & ChrW(7845) & "t"): Muc hK2, "(s" & ChrW(7855) & "p c" & ChrW(243) & ")", ""
        Gach hK
        Muc hK, "Thanh icon c" & ChrW(244) & "ng c" & ChrW(7909), ""
        Muc hK, "Bi" & ChrW(234) & "n t" & ChrW(7853) & "p " & ChrW(273) & ChrW(7889) & "i t" & ChrW(432) & ChrW(7907) & "ng", ""
        Muc hK, "Quy " & ChrW(273) & ChrW(7883) & "nh ph" & ChrW(226) & "n l" & ChrW(7899) & "p", "QDLOP"
        Muc hK, "Nh" & ChrW(227) & "n b" & ChrW(7843) & "n " & ChrW(273) & ChrW(7891) & " ki" & ChrW(7875) & "m k" & ChrW(234), ""

        hK = MenuCon(h, "B" & ChrW(7843) & "ng m" & ChrW(224) & "u s" & ChrW(7917) & " d" & ChrW(7909) & "ng khi t" & ChrW(244))
        kkMau = DC_DocCauHinh("KK_MAU", "0")
        MucTick hK, "T" & ChrW(244) & " theo ch" & ChrW(7881) & " s" & ChrW(7889) & " b" & ChrW(7843) & "ng m" & ChrW(224) & "u", "KKMAU:0", (kkMau <> "1")
        MucTick hK, "T" & ChrW(244) & " theo ch" & ChrW(7881) & " s" & ChrW(7889) & " m" & ChrW(224) & "u RGB", "KKMAU:1", (kkMau = "1")
        Gach h

        hK = MenuCon(h, "T" & ChrW(7841) & "o l" & ChrW(7853) & "p b" & ChrW(7843) & "n " & ChrW(273) & ChrW(7891) & " ki" & ChrW(7875) & "m k" & ChrW(234))
        Muc hK, "T" & ChrW(7921) & " " & ChrW(273) & ChrW(7897) & "ng t" & ChrW(236) & "m, s" & ChrW(7917) & "a l" & ChrW(7895) & "i khoanh " & ChrW(273) & ChrW(7845) & "t", "TIMLOI"
        Muc hK, "S" & ChrW(7917) & "a l" & ChrW(7895) & "i khoanh " & ChrW(273) & ChrW(7845) & "t th" & ChrW(7911) & " c" & ChrW(244) & "ng", ""
        Muc hK, "L" & ChrW(224) & "m tr" & ChrW(242) & "n s" & ChrW(7889) & " l" & ChrW(7867) & " t" & ChrW(7885) & "a " & ChrW(273) & ChrW(7897) & " " & ChrW(273) & ChrW(7881) & "nh ranh", "LAMTRON"
        Muc hK, "T" & ChrW(7841) & "o Topology b" & ChrW(7843) & "n " & ChrW(273) & ChrW(7891) & " ki" & ChrW(7875) & "m k" & ChrW(234), "TOPO"
        Muc hK, "T" & ChrW(7841) & "o khoanh " & ChrW(273) & ChrW(7845) & "t t" & ChrW(7915) & " b" & ChrW(7843) & "n " & ChrW(273) & ChrW(7891) & " " & ChrW(273) & ChrW(7883) & "a ch" & ChrW(237) & "nh", ""
        Gach hK
        Muc hK, "T" & ChrW(7841) & "o " & ChrW(273) & ChrW(432) & ChrW(7901) & "ng bao b" & ChrW(7843) & "n " & ChrW(273) & ChrW(7891) & " ki" & ChrW(7875) & "m k" & ChrW(234), ""
        Muc hK, "V" & ChrW(7869) & " nh" & ChrW(227) & "n t" & ChrW(7915) & " d" & ChrW(7919) & " li" & ChrW(7879) & "u Famis(*.pol)", ""

        hK = MenuCon(h, "Th" & ChrW(244) & "ng tin b" & ChrW(7843) & "n " & ChrW(273) & ChrW(7891) & " ki" & ChrW(7875) & "m k" & ChrW(234))
        Muc hK, ChrW(272) & ChrW(225) & "nh s" & ChrW(7889) & " th" & ChrW(7913) & " t" & ChrW(7921) & " khoanh " & ChrW(273) & ChrW(7845) & "t", ""
        Muc hK, "G" & ChrW(225) & "n th" & ChrW(244) & "ng tin khoanh " & ChrW(273) & ChrW(7845) & "t t" & ChrW(7915) & " nh" & ChrW(227) & "n", "GANTT"
        Muc hK, "C" & ChrW(7853) & "p nh" & ChrW(7853) & "t khoanh " & ChrW(273) & ChrW(7845) & "t ch" & ChrW(7885) & "n", ""
        Muc hK, "Qu" & ChrW(7843) & "n l" & ChrW(253) & " th" & ChrW(244) & "ng tin khoanh " & ChrW(273) & ChrW(7845) & "t", "BANGDL"
        Muc hK, "G" & ChrW(225) & "n s" & ChrW(7889) & " khoanh theo nh" & ChrW(227) & "n " & ChrW(273) & ChrW(7883) & "a ch" & ChrW(237) & "nh", ""

        hK = MenuCon(h, "Tr" & ChrW(236) & "nh b" & ChrW(224) & "y b" & ChrW(7843) & "n " & ChrW(273) & ChrW(7891) & " ki" & ChrW(7875) & "m k" & ChrW(234))
        Muc hK, "Xu" & ChrW(7845) & "t Polygon cho t" & ChrW(7915) & "ng khoanh " & ChrW(273) & ChrW(7845) & "t", "KKPOLY"
        Muc hK, "T" & ChrW(7841) & "o " & ChrW(273) & ChrW(432) & ChrW(7901) & "ng bao " & ChrW(273) & ChrW(7883) & "a gi" & ChrW(7899) & "i h" & ChrW(224) & "nh ch" & ChrW(237) & "nh", ""
        Muc hK, "V" & ChrW(7869) & " nh" & ChrW(227) & "n khoanh " & ChrW(273) & ChrW(7845) & "t b" & ChrW(7843) & "n " & ChrW(273) & ChrW(7891) & " ki" & ChrW(7875) & "m k" & ChrW(234), ""
        Muc hK, "V" & ChrW(7869) & " th" & ChrW(244) & "ng tin thu" & ChrW(7897) & "c t" & ChrW(237) & "nh d" & ChrW(7919) & " li" & ChrW(7879) & "u ki" & ChrW(7875) & "m k" & ChrW(234), ""
        Gach h

        hK = MenuCon(h, "B" & ChrW(7843) & "n " & ChrW(273) & ChrW(7891) & " hi" & ChrW(7879) & "n tr" & ChrW(7841) & "ng s" & ChrW(7917) & " d" & ChrW(7909) & "ng " & ChrW(273) & ChrW(7845) & "t")
        Muc hK, "T" & ChrW(244) & " m" & ChrW(224) & "u b" & ChrW(7843) & "n " & ChrW(273) & ChrW(7891) & " hi" & ChrW(7879) & "n tr" & ChrW(7841) & "ng (TT 08/2024)", "KKTOMAU"
        Muc hK, "V" & ChrW(7869) & " nh" & ChrW(227) & "n b" & ChrW(7843) & "n " & ChrW(273) & ChrW(7891) & " hi" & ChrW(7879) & "n tr" & ChrW(7841) & "ng", ""
        Gach hK
        Muc hK, "T" & ChrW(7841) & "o khung b" & ChrW(7843) & "n " & ChrW(273) & ChrW(7891) & " hi" & ChrW(7879) & "n tr" & ChrW(7841) & "ng", ""
        Muc hK, "T" & ChrW(7841) & "o b" & ChrW(7843) & "ng ch" & ChrW(250) & " d" & ChrW(7851) & "n b" & ChrW(7843) & "n " & ChrW(273) & ChrW(7891), ""
        Muc hK, "T" & ChrW(7841) & "o bi" & ChrW(7875) & "u " & ChrW(273) & ChrW(7891) & " c" & ChrW(417) & " c" & ChrW(7845) & "u s" & ChrW(7917) & " d" & ChrW(7909) & "ng " & ChrW(273) & ChrW(7845) & "t", ""
        Muc hK, "M" & ChrW(7851) & "u x" & ChrW(225) & "c nh" & ChrW(7853) & "n v" & ChrW(224) & " k" & ChrW(253) & " duy" & ChrW(7879) & "t", ""
        Muc hK, "K" & ChrW(253) & " hi" & ChrW(7879) & "u h" & ChrW(432) & ChrW(7899) & "ng b" & ChrW(7855) & "c tr" & ChrW(234) & "n b" & ChrW(7843) & "n " & ChrW(273) & ChrW(7891), ""
        hK = MenuCon(h, "Nh" & ChrW(7853) & "p, hi" & ChrW(7875) & "n th" & ChrW(7883) & " d" & ChrW(7919) & " li" & ChrW(7879) & "u " & ChrW(273) & ChrW(7883) & "a ch" & ChrW(237) & "nh"): Muc hK, "(s" & ChrW(7855) & "p c" & ChrW(243) & ")", ""
        hK = MenuCon(h, "Ki" & ChrW(7875) & "m tra chu" & ChrW(7849) & "n h" & ChrW(243) & "a d" & ChrW(7919) & " li" & ChrW(7879) & "u"): Muc hK, "(s" & ChrW(7855) & "p c" & ChrW(243) & ")", ""
        hK = MenuCon(h, "Xu" & ChrW(7845) & "t bi" & ChrW(7875) & "u th" & ChrW(7889) & "ng k" & ChrW(234) & ", ki" & ChrW(7875) & "m k" & ChrW(234)): Muc hK, "(s" & ChrW(7855) & "p c" & ChrW(243) & ")", ""
        Gach h
        hK = MenuCon(h, "Xu" & ChrW(7845) & "t d" & ChrW(7919) & " li" & ChrW(7879) & "u b" & ChrW(225) & "o c" & ChrW(225) & "o, giao n" & ChrW(7897) & "p"): Muc hK, "(s" & ChrW(7855) & "p c" & ChrW(243) & ")", ""

    Case "TIENICH"
        Muc h, "Tr" & ChrW(237) & "ch l" & ChrW(7909) & "c th" & ChrW(7917) & "a " & ChrW(273) & ChrW(7845) & "t", "TRICHLUC"
        Gach h
        Muc h, "Xem b" & ChrW(7843) & "n " & ChrW(273) & ChrW(7891) & " tr" & ChrW(234) & "n " & ChrW(7843) & "nh v" & ChrW(7879) & " tinh", "VETINH"
        Muc h, "M" & ChrW(7903) & " b" & ChrW(7857) & "ng Google Earth Pro (KML)", "GEARTH"
        Gach h
        Muc h, "Xu" & ChrW(7845) & "t d" & ChrW(7919) & " li" & ChrW(7879) & "u", ""
        Gach h
        Muc h, "B" & ChrW(7853) & "t t" & ChrW(7845) & "t c" & ChrW(7843) & " c" & ChrW(225) & "c l" & ChrW(7899) & "p", "BATLOP"
        Muc h, "T" & ChrW(7855) & "t t" & ChrW(7845) & "t c" & ChrW(7843) & " c" & ChrW(225) & "c l" & ChrW(7899) & "p", "TATLOP"
        Muc h, "B" & ChrW(7853) & "t l" & ChrW(7899) & "p " & ChrW(273) & ChrW(7889) & "i t" & ChrW(432) & ChrW(7907) & "ng ch" & ChrW(7885) & "n (ch" & ChrW(7881) & " hi" & ChrW(7879) & "n l" & ChrW(7899) & "p " & ChrW(273) & ChrW(243) & ")", "BATLOPCHON"
        Muc h, "T" & ChrW(7855) & "t l" & ChrW(7899) & "p " & ChrW(273) & ChrW(7889) & "i t" & ChrW(432) & ChrW(7907) & "ng ch" & ChrW(7885) & "n", "TATLOPCHON"
        Muc h, "B" & ChrW(7853) & "t/t" & ChrW(7855) & "t theo nh" & ChrW(243) & "m l" & ChrW(7899) & "p (s" & ChrW(7855) & "p c" & ChrW(243) & ")", ""
        Gach h
        Muc h, "Ch" & ChrW(7885) & "n theo thu" & ChrW(7897) & "c t" & ChrW(237) & "nh " & ChrW(273) & ChrW(7889) & "i t" & ChrW(432) & ChrW(7907) & "ng ch" & ChrW(7885) & "n", "CHONTT"
        Muc h, "X" & ChrW(243) & "a theo thu" & ChrW(7897) & "c t" & ChrW(237) & "nh " & ChrW(273) & ChrW(7889) & "i t" & ChrW(432) & ChrW(7907) & "ng ch" & ChrW(7885) & "n", "XOATT"
        Muc h, "Ch" & ChrW(7885) & "n l" & ChrW(7899) & "p theo " & ChrW(273) & ChrW(7889) & "i t" & ChrW(432) & ChrW(7907) & "ng ch" & ChrW(7885) & "n", "CHONLOP"
        Muc h, "X" & ChrW(243) & "a l" & ChrW(7899) & "p " & ChrW(273) & ChrW(7889) & "i t" & ChrW(432) & ChrW(7907) & "ng " & ChrW(273) & ChrW(432) & ChrW(7907) & "c ch" & ChrW(7885) & "n", "XOALOP"
        Muc h, "T" & ChrW(225) & "ch l" & ChrW(7899) & "p nh" & ChrW(227) & "n (lo" & ChrW(7841) & "i " & ChrW(273) & ChrW(7845) & "t / s" & ChrW(7889) & " th" & ChrW(7917) & "a / di" & ChrW(7879) & "n t" & ChrW(237) & "ch)", "TACHLOP"
        Muc h, "Th" & ChrW(7921) & "c hi" & ChrW(7879) & "n t" & ChrW(7853) & "p l" & ChrW(7879) & "nh theo " & ChrW(273) & ChrW(7883) & "nh ngh" & ChrW(297) & "a (s" & ChrW(7855) & "p c" & ChrW(243) & ")", ""
        Gach h
        Muc h, "Chi" & ChrW(7873) & "u d" & ChrW(224) & "i c" & ChrW(7841) & "nh...", "GHICD"
        Muc h, "Ki" & ChrW(7875) & "m tra v" & ChrW(249) & "ng th" & ChrW(7917) & "a (giao n" & ChrW(7897) & "p TW)", "KTVUNG"     ' SUA 05/11
        Muc h, "Convert Font TCVN3 - Unicode", "DOIFONT"
        Muc h, "Convert Font nhi" & ChrW(7873) & "u file (TCVN3 / Unicode)...", "CFONT"
        Muc h, "G" & ChrW(7855) & "n tag b" & ChrW(7843) & "ng t" & ChrW(7885) & "a " & ChrW(273) & ChrW(7897) & " (l" & ChrW(224) & "m file m" & ChrW(7851) & "u tr" & ChrW(237) & "ch l" & ChrW(7909) & "c)...", "GANTAG"

    Case "TROGIUP"
        Dim hTL As Long
        hTL = MenuCon(h, "Tr" & ChrW(7907) & " l" & ChrW(253) & " l" & ChrW(7879) & "nh (g" & ChrW(245) & " ti" & ChrW(7871) & "ng Vi" & ChrW(7879) & "t)")
        Muc hTL, "Tr" & ChrW(237) & "ch l" & ChrW(7909) & "c b" & ChrW(7843) & "n " & ChrW(273) & ChrW(7891) & " " & ChrW(273) & ChrW(7883) & "a ch" & ChrW(237) & "nh (TT26)", "TROLY:0"
        Muc hTL, "T" & ChrW(225) & "ch th" & ChrW(7917) & "a " & ChrW(273) & ChrW(7845) & "t (TT26 - m" & ChrW(7851) & "u 22/" & ChrW(272) & "K)", "TROLY:1"
        Muc hTL, "H" & ChrW(7907) & "p th" & ChrW(7917) & "a " & ChrW(273) & ChrW(7845) & "t (TT26 - m" & ChrW(7851) & "u 22/" & ChrW(272) & "K)", "TROLY:2"
        Muc hTL, "Tr" & ChrW(237) & "ch l" & ChrW(7909) & "c + Phi" & ChrW(7871) & "u " & ChrW(273) & "o " & ChrW(273) & ChrW(7841) & "c ch" & ChrW(7881) & "nh l" & ChrW(253) & " (m" & ChrW(7851) & "u VL)", "TROLY:3"
        Gach h
        Muc h, "H" & ChrW(432) & ChrW(7899) & "ng d" & ChrW(7851) & "n s" & ChrW(7917) & " d" & ChrW(7909) & "ng", "HUONGDAN"
        Muc h, "Ki" & ChrW(7875) & "m tra c" & ChrW(7853) & "p nh" & ChrW(7853) & "t...", "CAPNHAT"
        Gach h
        Muc h, "Gi" & ChrW(7899) & "i thi" & ChrW(7879) & "u", "GIOITHIEU"
    End Select

    TaoMenu = h
End Function

'============================================================
' THUC THI LENH THEO MA  (them Case khi co cong cu moi)
'============================================================
Public Sub DC_ChayLenh(ByVal ma As String)
    Select Case ma
    Case "TOPO":      DC_MoTaoThua
    Case "TIMLOI":    DC_MoTimLoi
    Case "KTVUNG":    DC_MoKiemVung          ' SUA 05/11: moi vung 1 so thua / 1 loai dat / 1 dien tich
    Case "GANTT":     DC_MoGanTT
    Case "BANGDL":    DC_MoBangDuLieu
    Case "VENHAN":    DC_MoVeNhan            ' SUA 25/10: form Ve nhan thua (modVeNhan)
    Case "TRICHLUC":  DC_MoTrichLuc
    Case "GANNHAN":   DC_MoGanNhan
    Case "CHIADOAN":  DC_MoChiaDoan
    Case "BATLOP":     DC_BatTatCaLop
    Case "TATLOP":     DC_TatTatCaLop
    Case "BATLOPCHON": DC_BatLopDoiTuongChon
    Case "TATLOPCHON": DC_TatLopDoiTuongChon
    Case "CHONTT":     DC_ChonTheoThuocTinh
    Case "XOATT":      DC_XoaTheoThuocTinh
    Case "CHONLOP":    DC_ChonTheoLop
    Case "XOALOP":     DC_XoaLopDoiTuongChon
    Case "TACHLOP":    DC_MoTachLop
    Case "TROLY":      DC_MoTroLy
    Case "GHICD":      DC_MoChieuDaiCanh      ' SUA 17/10: form kieu "Ban do canh" (modChieuDai)
    Case "DOIFONT":    DC_DoiFontTcvn3
    Case "CFONT":      DC_MoConvertFont
    Case "GANTAG":     DC_GanTagBang
    Case "TDTOADO":    DC_TDToaDo
    Case "TDGOCCANH":  DC_TDGocCanh
    Case "TRIENDS":    DC_MoDiemMia
    Case "CANHNGAN":   DC_TimCanhNgan
    Case "LAMTRON":    DC_LamTronToaDo
    Case "GOCNHO":     DC_TimGocNho
    Case "QDLOP":      DC_QuyDinhLop
    Case "KKPOLY":     DC_XuatPolygonKhoanh
    Case "KKTOMAU":    DC_ToMauHienTrang
    Case "VETINH":    DC_MoChonKTT "VETINH"     ' SUA 18/10: chon tinh / KTT truoc
    Case "GEARTH":    DC_MoChonKTT "GEARTH"
    Case "MACDINH"
        DC_MacDinh
        DC_ThongBao ChrW(272) & ChrW(227) & " " & ChrW(273) & ChrW(7863) & "t: Line Style 0, Weight 0, font Times New Roman.", "Thi" & ChrW(7871) & "t l" & ChrW(7853) & "p"
    Case "DONVIHC":   frmDonViHC.Show vbModeless
    Case "THUMUC":    MoThuMuc
    Case "HUONGDAN":  MoHuongDan
    Case "GIOITHIEU": DC_GioiThieu
    Case "CAPNHAT"
        ' chay sau khi thoat su kien menu (khong sua code form dang chay)
        Unload frmDiaChinh
        CadInputQueue.SendKeyin "vba run [DiaChinhVL]modCapNhatWeb.DC_KiemTraCapNhat"
    Case "DONG":      Unload frmDiaChinh
    Case Else
        If Left$(ma, 3) = "BT:" Then DC_BienTap Mid$(ma, 4): Exit Sub
        If Left$(ma, 3) = "TY:" Then DC_DatTyLeBD CLng(val(Mid$(ma, 4))): Exit Sub
        If Left$(ma, 6) = "KKMAU:" Then DC_DatBangMauKK Mid$(ma, 7): Exit Sub
        If Left$(ma, 6) = "TROLY:" Then DC_MoTroLyMau CLng(val(Mid$(ma, 7))): Exit Sub
        DC_ThongBao "Ch" & ChrW(7913) & "c n" & ChrW(259) & "ng " & ChrW(273) & "ang ph" & ChrW(225) & "t tri" & ChrW(7875) & "n.", ChrW(272) & ChrW(7883) & "a Ch" & ChrW(237) & "nh VL"
    End Select
End Sub

'============================================================
' Hien popup menu ngay duoi nhan menu tren form.
'   x, y     : toa do chuot trong nhan (point, tu su kien MouseDown)
'   caoNhan  : chieu cao nhan (point)
' Tra ve ma lenh da chon ("" neu bam ra ngoai)
'============================================================
Public Function DC_HienMenu(ByVal ten As String, ByVal tieuDe As String, _
                            ByVal x As Single, ByVal y As Single, _
                            ByVal caoNhan As Single) As String
    Dim h As Long, hw As Long, id As Long, k As Double
    Dim p As POINTAPI

    h = TaoMenu(ten)
    If h = 0 Then Exit Function

    GetCursorPos p
    k = HeSoDpi()
    hw = FindWindowA("ThunderDFrame", tieuDe)
    If hw = 0 Then hw = GetForegroundWindow()
    SetForegroundWindow hw

    id = TrackPopupMenu(h, TPM_RETURNCMD Or TPM_NONOTIFY Or TPM_LEFTBUTTON, _
                        CLng(p.x - x * k), CLng(p.y + (caoNhan - y) * k), 0, hw, 0)
    DestroyMenu h

    If id >= 1 And id <= mN Then DC_HienMenu = mMa(id)
End Function

'============================================================
' Hop thong bao Unicode (chu Viet day du, khong bi "?")
'   kieu: vbInformation / vbExclamation / vbCritical / vbYesNo...
'============================================================
Public Function DC_ThongBao(ByVal noiDung As String, _
                            Optional ByVal tieuDe As String = "", _
                            Optional ByVal kieu As Long = vbInformation) As Long
    If Len(tieuDe) = 0 Then tieuDe = ChrW(272) & ChrW(7883) & "a Ch" & ChrW(237) & "nh VL"
    DC_ThongBao = MessageBoxW(GetForegroundWindow(), StrPtr(noiDung), StrPtr(tieuDe), kieu)
End Function

'------------------------------------------------------------
Private Sub Muc(ByVal h As Long, ByVal cap As String, ByVal ma As String)
    mN = mN + 1
    ReDim Preserve mMa(1 To mN)
    mMa(mN) = ma
    If Len(ma) = 0 Then
        AppendMenuW h, MF_STRING Or MF_GRAYED, mN, StrPtr(cap)
    Else
        AppendMenuW h, MF_STRING, mN, StrPtr(cap)
    End If
End Sub

Private Sub MucTick(ByVal h As Long, ByVal cap As String, ByVal ma As String, ByVal tick As Boolean)
    mN = mN + 1
    ReDim Preserve mMa(1 To mN)
    mMa(mN) = ma
    AppendMenuW h, MF_STRING Or IIf(tick, MF_CHECKED, 0), mN, StrPtr(cap)
End Sub

' Menu con theo nhom trong bang Quy dinh lop (modBienTap). K = ky hieu chua lam -> mo.
Private Sub NhomBT(ByVal h As Long, ByVal nhom As String, ByVal cap As String)
    Dim dS As Collection, i As Long, hc As Long, r As Variant, loaiTruoc As String, coMuc As Boolean
    hc = MenuCon(h, cap)
    If hc = 0 Then Exit Sub
    Set dS = BT_DocBang()
    For i = 1 To dS.Count
        r = dS.Item(i)
        If StrComp(r(0), nhom, vbTextCompare) = 0 Then
            If coMuc And UCase$(r(3)) <> loaiTruoc And loaiTruoc = "L" Then Gach hc
            If UCase$(r(3)) = "K" Then
                Muc hc, r(2), ""
            Else
                Muc hc, r(2), "BT:" & r(1)
            End If
            loaiTruoc = UCase$(r(3)): coMuc = True
        End If
    Next i
    If Not coMuc Then Muc hc, "(ch" & ChrW(432) & "a c" & ChrW(243) & " trong Quy " & ChrW(273) & ChrW(7883) & "nh l" & ChrW(7899) & "p)", ""
End Sub

' Menu con (submenu); id cac muc trong menu con dung chung day so mN
Private Function MenuCon(ByVal h As Long, ByVal cap As String) As Long
    Dim hc As Long
    hc = CreatePopupMenu()
    If hc = 0 Then Exit Function
    AppendMenuW h, MF_POPUP, hc, StrPtr(cap)
    MenuCon = hc
End Function

Private Sub Gach(ByVal h As Long)
    AppendMenuW h, MF_SEPARATOR, 0, 0
End Sub

Private Function HeSoDpi() As Double
    Dim hdc As Long, dpi As Long
    hdc = GetDC(0)
    dpi = GetDeviceCaps(hdc, LOGPIXELSX)
    ReleaseDC 0, hdc
    If dpi <= 0 Then dpi = 96
    HeSoDpi = dpi / 72#
End Function

'============================================================
' Gan logo (file .ico) len thanh tieu de cua form.
'   Goi trong UserForm_Activate (luc do cua so da ton tai).
'   Khong co file icon -> bo qua, khong bao loi.
'============================================================
Public Sub DC_GanIcon(ByVal tieuDe As String)
    On Error Resume Next
    Dim hw As Long, hNho As Long, hLon As Long, ex As Long
    If Len(Dir$(DC_ICON)) = 0 Then Exit Sub
    hw = FindWindowA("ThunderDFrame", tieuDe)
    If hw = 0 Then Exit Sub

    ' bo kieu khung hop thoai -> Windows moi ve icon o goc trai
    ex = GetWindowLongA(hw, GWL_EXSTYLE)
    SetWindowLongA hw, GWL_EXSTYLE, ex And Not WS_EX_DLGMODALFRAME

    hNho = LoadImageA(0, DC_ICON, IMAGE_ICON, 16, 16, LR_LOADFROMFILE)
    hLon = LoadImageA(0, DC_ICON, IMAGE_ICON, 32, 32, LR_LOADFROMFILE)
    If hNho <> 0 Then SendMessageA hw, WM_SETICON, ICON_SMALL, hNho
    If hLon <> 0 Then SendMessageA hw, WM_SETICON, ICON_BIG, hLon

    SetWindowPos hw, 0, 0, 0, 0, 0, SWP_FLAGS
End Sub

Private Sub MoThuMuc()
    If Len(Dir$(DC_THUMUC, vbDirectory)) = 0 Then
        DC_ThongBao "Ch" & ChrW(432) & "a c" & ChrW(243) & " th" & ChrW(432) & " m" & ChrW(7909) & "c " & DC_THUMUC & ". H" & ChrW(227) & "y ch" & ChrW(7841) & "y CaiDat_DiaChinhVL.bat.", ChrW(272) & ChrW(7883) & "a Ch" & ChrW(237) & "nh VL", vbExclamation
        Exit Sub
    End If
    Shell "explorer.exe """ & DC_THUMUC & """", vbNormalFocus
End Sub

Private Sub MoHuongDan()
    Dim f As String
    f = DC_THUMUC & "\HuongDan_DiaChinhVL.docx"
    If Len(Dir$(f)) = 0 Then
        DC_ThongBao "Kh" & ChrW(244) & "ng th" & ChrW(7845) & "y file h" & ChrW(432) & ChrW(7899) & "ng d" & ChrW(7851) & "n:" & vbCrLf & f, "H" & ChrW(432) & ChrW(7899) & "ng d" & ChrW(7851) & "n", vbExclamation
        Exit Sub
    End If
    Shell "cmd /c start """" """ & f & """", vbHide
End Sub

Attribute VB_Name = "modMoBangDuLieu"
Option Explicit

'============================================================
' Mo bang du lieu thua dat (kieu gCadas) - form frmBangDuLieu
'============================================================
Public Sub DC_MoBangDuLieu()
    frmBangDuLieu.Show vbModeless
End Sub

Attribute VB_Name = "modMoGanNhan"
Option Explicit

Public Sub DC_MoGanNhan()
    frmGanNhan.Show vbModeless
End Sub

Attribute VB_Name = "modMoGanTT"
Option Explicit

Public Sub DC_MoGanTT()
    frmGanTT.Show vbModeless
End Sub

'============================================================
' Ham xu ly goi tu form: gan thong tin tu nhan vao CSDL + ve nhan
'============================================================
Public Sub ChayGanTT(ByVal path As String, ByVal lvSo As String, ByVal lvTo As String, _
                     ByVal lvLoai As String, ByVal lvChu As String, ByVal lvDC As String, _
                     ByVal lvNhan As String, ByVal cao As Double, ByVal veNhan As Boolean, _
                     Optional ByVal xoaCu As Boolean = False)
    Dim vungs As Collection
    Set vungs = MoCSDL(path)
    If vungs.Count = 0 Then MsgBox "CSDL rong / khong doc duoc: " & path, vbExclamation: Exit Sub

    ' SUA 13/10/2026: khong bat buoc level so thua; bao level nhap ma khong co
    Dim thieu As String, lvX As Variant
    For Each lvX In Array(lvSo, lvTo, lvLoai, lvChu, lvDC)
        If Len(Trim$(lvX)) > 0 Then
            If DC_TimLevel(CStr(lvX)) Is Nothing Then thieu = thieu & " " & Trim$(lvX)
        End If
    Next lvX
    If Len(thieu) > 0 Then
        DC_ThongBao "Kh" & ChrW(244) & "ng t" & ChrW(236) & "m th" & ChrW(7845) & "y level:" & thieu & vbCrLf & "(G" & ChrW(245) & " s" & ChrW(7889) & " level, v" & ChrW(237) & " d" & ChrW(7909) & " 13)", "G" & ChrW(225) & "n th" & ChrW(244) & "ng tin", vbExclamation
        Exit Sub
    End If
    If xoaCu Then
        Dim k As Long, vx As clsVung
        For k = 1 To vungs.Count
            Set vx = vungs.Item(k)
            If Len(Trim$(lvSo)) > 0 Then vx.soThua = ""
            If Len(Trim$(lvTo)) > 0 Then vx.SoTo = ""
            If Len(Trim$(lvLoai)) > 0 Then vx.loaiDat = ""
            If Len(Trim$(lvChu)) > 0 Then vx.TenChu = ""
            If Len(Trim$(lvDC)) > 0 Then vx.DiaChi = ""
        Next k
    End If

    Dim nSo As Long, nTo As Long, nLoai As Long, nChu As Long, nDC As Long
    nSo = GanTruongCSDL2(vungs, lvSo, "so_thua")
    nTo = GanTruongCSDL2(vungs, lvTo, "so_to")
    nLoai = GanTruongCSDL2(vungs, lvLoai, "loai_dat")
    nChu = GanTruongCSDL2(vungs, lvChu, "ten_chu")
    nDC = GanTruongCSDL2(vungs, lvDC, "dia_chi")

    Dim ok As Boolean
    ok = LuuCSDL(vungs, path)

    If veNhan Then
        If cao <= 0 Then cao = 1
        If Len(Trim$(lvNhan)) > 0 Then
            On Error Resume Next
            Set ActiveSettings.Level = DC_TimLevel(lvNhan)
            On Error GoTo 0
        End If
        Dim i As Long, v As clsVung
        For i = 1 To vungs.Count
            Set v = vungs.Item(i)
            VeNhanTT26 v, cao        ' SUA 25/10: nhan TT26 thanh 1 khoi (cell)
        Next i
    End If

    DC_ThongBao "S" & ChrW(7889) & " th" & ChrW(7917) & "a: " & vungs.Count & vbCrLf & _
           "G" & ChrW(225) & "n s" & ChrW(7889) & " th" & ChrW(7917) & "a: " & nSo & " ; t" & ChrW(7901) & ": " & nTo & " ; lo" & ChrW(7841) & "i " & ChrW(273) & ChrW(7845) & "t: " & nLoai & vbCrLf & _
           "T" & ChrW(234) & "n ch" & ChrW(7911) & ": " & nChu & " ; " & ChrW(273) & ChrW(7883) & "a ch" & ChrW(7881) & ": " & nDC & vbCrLf & _
           IIf(ok, ChrW(272) & ChrW(227) & " c" & ChrW(7853) & "p nh" & ChrW(7853) & "t CSDL.", "KH" & ChrW(212) & "NG l" & ChrW(432) & "u " & ChrW(273) & ChrW(432) & ChrW(7907) & "c CSDL!"), "G" & ChrW(225) & "n th" & ChrW(244) & "ng tin", IIf(ok, vbInformation, vbExclamation)
End Sub

'--- gan 1 truong (dung rieng cho module nay) ---
Private Function GanTruongCSDL2(ByVal vungs As Collection, ByVal levelName As String, _
                                ByVal truong As String) As Long
    If Len(Trim$(levelName)) = 0 Then Exit Function
    Dim esc As ElementScanCriteria
    Set esc = New ElementScanCriteria
    esc.ExcludeAllTypes
    esc.IncludeType msdElementTypeText
    esc.IncludeType msdElementTypeTextNode
    Dim lv As Level, lvSo As Long
    Set lv = DC_TimLevel(levelName)          ' go "13" = level so 13
    If lv Is Nothing Then Exit Function
    lvSo = lv.Number

    Dim ee As ElementEnumerator
    Set ee = ActiveModelReference.Scan(esc)
    Dim x As Double, y As Double, s As String, v As clsVung, dem As Long
    Do While ee.MoveNext
        If DC_LevelSo(ee.Current) = lvSo Then
        If DocText2(ee.Current, x, y, s) Then
            If Len(s) > 0 Then
                Set v = TimThuaChua(vungs, x, y)
                If Not v Is Nothing Then
                    ' SUA 13/10/2026: nhan tren ban do la dung -> ghi de (truoc chi gan khi trong,
                    ' nen loai dat mac dinh LUC khong bao gio duoc thay)
                    If LayTruong2(v, truong) <> s Then DatTruong2 v, truong, s
                    dem = dem + 1
                End If
            End If
        End If
        End If
    Loop
    GanTruongCSDL2 = dem
End Function

Private Function DocText2(ByVal el As Element, ByRef x As Double, _
                          ByRef y As Double, ByRef s As String) As Boolean
    DocText2 = False: s = ""
    Dim o As Point3d
    If el.Type = msdElementTypeText Then
        Dim oT As TextElement
        Set oT = el: o = oT.Origin: x = o.x: y = o.y: s = Trim$(oT.Text): DocText2 = True
    ElseIf el.Type = msdElementTypeTextNode Then
        Dim oNode As TextNodeElement
        Set oNode = el: o = oNode.Origin: x = o.x: y = o.y
        Dim subs As ElementEnumerator
        Set subs = oNode.GetSubElements
        Do While subs.MoveNext
            If subs.Current.Type = msdElementTypeText Then
                s = Trim$(subs.Current.AsTextElement.Text)
                If Len(s) > 0 Then Exit Do
            End If
        Loop
        DocText2 = True
    End If
End Function

Private Function LayTruong2(ByVal v As clsVung, ByVal t As String) As String
    Select Case t
        Case "so_thua": LayTruong2 = v.soThua
        Case "so_to": LayTruong2 = v.SoTo
        Case "loai_dat": LayTruong2 = v.loaiDat
        Case "ten_chu": LayTruong2 = v.TenChu
        Case "dia_chi": LayTruong2 = v.DiaChi
    End Select
End Function

Private Sub DatTruong2(ByVal v As clsVung, ByVal t As String, ByVal g As String)
    Select Case t
        Case "so_thua": v.soThua = g
        Case "so_to": v.SoTo = g
        Case "loai_dat": v.loaiDat = g
        Case "ten_chu": v.TenChu = g
        Case "dia_chi": v.DiaChi = g
    End Select
End Sub

'============================================================
' SUA 25/10: NHAN THUA THEO TT26 - 1 KHOI (cell "NHANTHUA"):
'   loai dat ben trai, so thua (tren) / dien tich (duoi) co gach ngang.
'   Ve bang mau / level / font dang dung (level lay tu o "Lop nhan").
'============================================================
Public Sub VeNhanTT26(ByVal v As clsVung, ByVal cao As Double)
    Dim tu As String, duoiS As String, loai As String
    Dim wTu As Double, wDt As Double, rong As Double, nua As Double, wl As Double
    Dim els() As Element, n As Long, cel As CellElement
    If v Is Nothing Then Exit Sub
    If cao <= 0 Then cao = 1
    tu = Trim$(v.soThua)
    duoiS = Replace(Format$(Round(v.dt, 1), "0.0"), ".", ",")
    loai = Trim$(v.loaiDat)
    If Len(tu) = 0 And v.dt <= 0 Then Exit Sub
    wTu = Len(tu) * cao * 0.6
    wDt = Len(duoiS) * cao * 0.6
    rong = wTu: If wDt > rong Then rong = wDt
    nua = rong / 2# + cao * 0.2

    On Error Resume Next
    ReDim els(0 To 3)
    Set els(n) = CreateLineElement2(Nothing, Point3dFromXYZ(v.cx - nua, v.cy, 0#), Point3dFromXYZ(v.cx + nua, v.cy, 0#))
    If Not els(n) Is Nothing Then n = n + 1
    If Len(tu) > 0 Then Set els(n) = ChuNhan(v.cx, v.cy + cao * 0.9, tu, cao): If Not els(n) Is Nothing Then n = n + 1
    If Len(duoiS) > 0 Then Set els(n) = ChuNhan(v.cx, v.cy - cao * 0.9, duoiS, cao): If Not els(n) Is Nothing Then n = n + 1
    If Len(loai) > 0 Then
        wl = Len(loai) * cao * 0.6
        Set els(n) = ChuNhan(v.cx - nua - wl / 2# - cao * 0.3, v.cy, loai, cao)
        If Not els(n) Is Nothing Then n = n + 1
    End If
    If n = 0 Then Exit Sub
    ReDim Preserve els(0 To n - 1)
    Err.Clear
    Set cel = CreateCellElement1("NHANTHUA", els, Point3dFromXYZ(v.cx, v.cy, 0#), False)
    If Not cel Is Nothing And Err.Number = 0 Then
        ActiveModelReference.AddElement cel
    Else
        ' khong tao duoc cell -> ve rieng tung phan tu
        Err.Clear
        Dim i As Long
        For i = 0 To n - 1
            ActiveModelReference.AddElement els(i)
        Next i
    End If
    Err.Clear
End Sub

Private Function ChuNhan(ByVal x As Double, ByVal y As Double, ByVal s As String, ByVal cao As Double) As Element
    Dim t As TextElement
    On Error Resume Next
    ActiveSettings.TextStyle.Height = cao
    ActiveSettings.TextStyle.Width = cao
    ActiveSettings.TextStyle.Justification = msdTextJustificationCenterCenter
    Set t = CreateTextElement1(Nothing, s, Point3dFromXYZ(x, y, 0#), Matrix3dIdentity)
    If Not t Is Nothing Then t.LineWeight = 0
    Set ChuNhan = t
End Function

Attribute VB_Name = "modMoGiaoDien"
Option Explicit

'============================================================
' modMoGiaoDien - Lenh mo menu + Gioi thieu + thiet lap mac dinh
'============================================================
Public Sub DC_MoGiaoDien()
    DC_MacDinh                       ' dat mac dinh moi lan mo tool
    frmDiaChinh.Show vbModeless
End Sub

'============================================================
' DAT MAC DINH KHI CHAY:
'   - Line Style = 0 , Line Weight = 0
'   - Font chu = Times New Roman (TrueType Unicode) -> go/ve duoc tieng Viet
' Dung SendKeyin cho chac (ap cho ca ve tay lan code cua tool, vi code
' tao Line/Text deu ke thua ActiveSettings).
'============================================================
Public Sub DC_MacDinh()
    On Error Resume Next
    CadInputQueue.SendKeyin "ACTIVE STYLE 0"
    CadInputQueue.SendKeyin "ACTIVE WEIGHT 0"
    CadInputQueue.SendKeyin "ACTIVE FONT " & Chr$(34) & "Times New Roman" & Chr$(34)
    DC_DatFontViet                   ' dat truc tiep (key-in tren chi chay sau khi macro xong)
    On Error GoTo 0
End Sub

Public Sub DC_GioiThieu()
    frmGioiThieu.Show vbModeless
End Sub

Attribute VB_Name = "modMoTaoThua"
Option Explicit

Public Sub DC_MoTaoThua()
    frmTaoThua.Show vbModeless
End Sub

Attribute VB_Name = "modMoTimLoi"
Option Explicit

'============================================================
' Mo hop thoai tim loi
'============================================================
Public Sub DC_MoTimLoi()
    frmTimLoi2.Show vbModeless
End Sub

Attribute VB_Name = "modMoTrichLuc"
Option Explicit

' Khung mau Phu luc 19 (doc tu file mau): o so do (level 24) + bao ngoai (dong H)
Private mBoxW As Double, mBoxH As Double, mBoxCX As Double, mBoxCY As Double
Private mHx1 As Double, mHy1 As Double, mHx2 As Double, mHy2 As Double

' View de zoom sau khi xuat (clsChonThuaTL dat = view vua bam)
Public gViewTL As View

' Pham vi + ten trich luc vua xuat (nut "Luu file ho so")
Public gTLx1 As Double, gTLy1 As Double, gTLx2 As Double, gTLy2 As Double
Public gTLTen As String

' Trang thai truoc khi "Tat lop ban do" (de "Bat lop ban do" tra lai dung nhu cu)
Private mLvTat As Collection      ' "chiSoView|tenLevel"
Private mAttTat As Collection     ' ten file tham chieu da tat

Public Sub DC_MoTrichLuc()
    frmTrichLuc.Show vbModeless
End Sub

'============================================================
' Chay trich luc: doc thua tu CSDL theo so thua -> ve
'   cheDoMau = True  : chen khung Phu luc 19
'   cheDoMau = False : chi so do + bang toa do tu ve
'============================================================
Public Sub ChayTrichLuc(ByVal csdlPath As String, ByVal soThua As String, _
                        ByVal mauPath As String, ByVal kieu As String, _
                        ByVal toBanDo As String, ByVal tenXa As String, _
                        ByVal tenHuyen As String, ByVal tenTinh As String, _
                        ByVal lvXuat As String, ByVal cao As Double, _
                        ByVal cheDoMau As Boolean, ByVal tyLe As Double)

    Dim vungs As Collection
    Set vungs = MoCSDL(csdlPath)
    If vungs.Count = 0 Then
        DC_ThongBao "CSDL r" & ChrW(7895) & "ng / kh" & ChrW(244) & "ng " & ChrW(273) & ChrW(7885) & "c " & ChrW(273) & ChrW(432) & ChrW(7907) & "c: " & csdlPath, "Tr" & ChrW(237) & "ch l" & ChrW(7909) & "c", vbExclamation
        Exit Sub
    End If

    Dim i As Long, v As clsVung, found As clsVung
    For i = 1 To vungs.Count
        Set v = vungs.Item(i)
        If Trim$(v.soThua) = Trim$(soThua) Then Set found = v: Exit For
    Next i
    If found Is Nothing Then
        DC_ThongBao "Kh" & ChrW(244) & "ng t" & ChrW(236) & "m th" & ChrW(7845) & "y th" & ChrW(7917) & "a s" & ChrW(7889) & " " & soThua & " trong CSDL." & vbCrLf & _
                    "(Th" & ChrW(7917) & "a ch" & ChrW(432) & "a g" & ChrW(225) & "n s" & ChrW(7889) & ": d" & ChrW(249) & "ng n" & ChrW(250) & "t Ch" & ChrW(7885) & "n th" & ChrW(7917) & "a tr" & ChrW(234) & "n b" & ChrW(7843) & "n " & ChrW(273) & ChrW(7891) & ")", "Tr" & ChrW(237) & "ch l" & ChrW(7909) & "c", vbExclamation
        Exit Sub
    End If

    ChayTrichLucThua found, mauPath, kieu, toBanDo, tenXa, tenHuyen, tenTinh, lvXuat, cao, cheDoMau, tyLe
End Sub

'============================================================
' Trich luc 1 thua da co san (vung topology). Thua chua gan thong tin
' van xuat duoc: so thua = 0, loai dat = 0, dien tich tu tinh.
'============================================================
Public Sub ChayTrichLucThua(ByVal found As clsVung, _
                            ByVal mauPath As String, ByVal kieu As String, _
                            ByVal toBanDo As String, ByVal tenXa As String, _
                            ByVal tenHuyen As String, ByVal tenTinh As String, _
                            ByVal lvXuat As String, ByVal cao As Double, _
                            ByVal cheDoMau As Boolean, ByVal tyLe As Double)

    ' SUA 16/10/2026: lan truoc da tu tat lop -> bat lai truoc khi xuat thua moi
    If DC_DaTatLop() Then DC_BatLopBanDo
    ' File mau .dgn (kieu gCadas) -> bat mau ra .txt (co cache)
    mauPath = DC_ChuanBiMau(mauPath)

    ' Bat buoc font TrueType co chu Viet (may moi chua dat font -> mat chu)
    If Not DC_DatFontViet() Then
        DC_ThongBao "Kh" & ChrW(244) & "ng " & ChrW(273) & ChrW(7863) & "t " & ChrW(273) & ChrW(432) & ChrW(7907) & "c font " & DC_FONT_VIET & " cho ch" & ChrW(7919) & "." & vbCrLf & _
                    "Ch" & ChrW(7919) & " ti" & ChrW(7871) & "ng Vi" & ChrW(7879) & "t tr" & ChrW(234) & "n tr" & ChrW(237) & "ch l" & ChrW(7909) & "c c" & ChrW(243) & " th" & ChrW(7875) & " kh" & ChrW(244) & "ng hi" & ChrW(7879) & "n.", "Tr" & ChrW(237) & "ch l" & ChrW(7909) & "c", vbExclamation
    End If

    ' Thua chua gan thong tin -> gia tri mac dinh
    If Len(Trim$(found.soThua)) = 0 Then found.soThua = "0"
    If Len(Trim$(found.loaiDat)) = 0 Then found.loaiDat = "0"
    If found.dt <= 0 Then found.dt = DienTichVung(found)
    ' SUA 12/10/2026: dinh 1 = tren-trai, danh so theo chieu kim dong ho
    ChuanHoaVong found

    ' Dat level xuat (go so "50" hoac ten "Level 50")
    If Len(Trim$(lvXuat)) > 0 Then
        On Error Resume Next
        Set ActiveSettings.Level = DC_TimLevel(lvXuat)
        On Error GoTo 0
    End If

    If Len(Trim$(toBanDo)) = 0 Then toBanDo = found.SoTo
    If Len(Trim$(toBanDo)) = 0 Then toBanDo = DC_ToTheoTenFile()    ' SUA 22/10: so trong ten file (DC9 -> 9)
    If Len(Trim$(toBanDo)) = 0 Then toBanDo = "0"
    If cao <= 0 Then cao = 1

    ' Ty le tu dong (tyLe = 0): ty le chuan nho nhat de thua vua o so do
    Dim tuDong As Boolean
    If tyLe <= 0 And cheDoMau Then
        tyLe = TyLeTuDong(found, mauPath)
        tuDong = True
    End If

    Dim zx1 As Double, zy1 As Double, zx2 As Double, zy2 As Double
    If cheDoMau Then
        gTyLeTuDong = tuDong
        ChenKhungTuThua found, mauPath, kieu, toBanDo, tenXa, tenHuyen, tenTinh, tyLe
        DC_TraMauDien     ' SUA 22/10: tra mau dang dung
        ' pham vi khung vua ve (khung dat tam o so do tai tam thua)
        If DocKhungMau(mauPath) Then
            zx1 = gTLCx + (mHx1 - mBoxCX) * tyLe / 20000#
            zx2 = gTLCx + (mHx2 - mBoxCX) * tyLe / 20000#
            zy1 = gTLCy + (mHy1 - mBoxCY) * tyLe / 20000#
            zy2 = gTLCy + (mHy2 - mBoxCY) * tyLe / 20000#
        End If
    Else
        Dim kx2 As Double, ky2 As Double, le As Double
        le = cao * 6#
        VeKhungTrichLuc found, le, kx2, ky2, 0
        VeSoDoThua found, cao, 0
        VeNhanThuaDayDu found, cao, "mau"
        VeBangToaDo found, kx2 + cao * 3#, ky2, cao, 0
    End If
    If zx2 <= zx1 Then
        ' so do tu ve / khong doc duoc mau: zoom quanh thua
        BaoThua found, zx1, zy1, zx2, zy2
        Dim r As Double
        r = (zx2 - zx1) + (zy2 - zy1)
        zx1 = zx1 - r: zx2 = zx2 + r * 2#: zy1 = zy1 - r: zy2 = zy2 + r
    End If
    gTLx1 = zx1: gTLy1 = zy1: gTLx2 = zx2: gTLy2 = zy2
    gTLTen = "TL_To" & toBanDo & "_Thua" & found.soThua
    DC_ZoomVung zx1, zy1, zx2, zy2
    ' SUA 16/10/2026: xuat xong TU TAT lop ban do, chi de Level ho so + Level so do
    '   (tat tinh nang: DiaChinhVL.ini -> TL_TUTATLOP=0)
    If DC_DocCauHinh("TL_TUTATLOP", "1") = "1" And DC_DocCauHinh("LV_HS_ON", "1") = "1" _
       And DC_DocCauHinh("LV_SD_ON", "1") = "1" Then
        If Len(Trim$(DC_DocCauHinh("LV_HS", ""))) > 0 And Len(Trim$(DC_DocCauHinh("LV_SD", ""))) > 0 Then
            DC_TatLopBanDo DC_DocCauHinh("LV_HS", ""), DC_DocCauHinh("LV_SD", "")
        End If
    End If

    DC_ThongBao ChrW(272) & ChrW(227) & " tr" & ChrW(237) & "ch l" & ChrW(7909) & "c th" & ChrW(7917) & "a s" & ChrW(7889) & " " & found.soThua & _
           " (di" & ChrW(7879) & "n t" & ChrW(237) & "ch " & Format$(Round(found.dt, 1), "0.0") & " m2)." & vbCrLf & _
           IIf(cheDoMau, "Ki" & ChrW(7875) & "u: khung Ph" & ChrW(7909) & " l" & ChrW(7909) & "c 19 - t" & ChrW(7927) & " l" & ChrW(7879) & " 1:" & CStr(tyLe) & IIf(tuDong, " (t" & ChrW(7921) & " " & ChrW(273) & ChrW(7897) & "ng)", ""), "Ki" & ChrW(7875) & "u: s" & ChrW(417) & " " & ChrW(273) & ChrW(7891) & " t" & ChrW(7921) & " v" & ChrW(7869)), "Tr" & ChrW(237) & "ch l" & ChrW(7909) & "c"
End Sub

'--- dien tich tu ranh (cong thuc Gauss), tru dien tich dao
Private Function DienTichVung(ByVal v As clsVung) As Double
    Dim r() As Double, s As Double, k As Long
    On Error Resume Next
    If Not v.HasRing Then Exit Function
    r = v.ring
    s = Abs(DtMang(r))
    For k = 1 To v.dao.Count
        s = s - Abs(DtMang(v.dao.Item(k)))
    Next k
    DienTichVung = s
End Function

'============================================================
' TY LE TU DONG: ty le chuan nho nhat de thua nam vua o so do (90%)
' o ty le that (kp = 1). O so do = level 24 cua mau, quy doi
' kich thuoc that = kich thuoc mau * tyLe / 20000 (xem modKhungMau).
'============================================================
Private Function TyLeTuDong(ByVal v As clsVung, ByVal mauPath As String) As Double
    Dim dS As Variant, i As Long, pw As Double, pH As Double
    Dim x1 As Double, y1 As Double, x2 As Double, y2 As Double
    dS = Array(200#, 500#, 700#, 1000#, 2000#, 5000#, 10000#)
    If Not DocKhungMau(mauPath) Then mBoxW = 989.8: mBoxH = 1048#
    BaoThua v, x1, y1, x2, y2
    pw = x2 - x1: pH = y2 - y1
    For i = LBound(dS) To UBound(dS)
        If pw <= mBoxW * dS(i) / 20000# * 0.9 And pH <= mBoxH * dS(i) / 20000# * 0.9 Then
            TyLeTuDong = dS(i): Exit Function
        End If
    Next i
    TyLeTuDong = 10000#      ' qua lon: giu 1:10000, so do tu thu nho
End Function

' Doc o so do (L 24) va bao ngoai (H) tu file mau
Private Function DocKhungMau(ByVal path As String) As Boolean
    Dim st As Object, txt As String, Dong() As String, p() As String
    Dim i As Long, j As Long, co As Boolean
    Dim bx1 As Double, by1 As Double, bx2 As Double, by2 As Double, x As Double, y As Double
    On Error Resume Next
    Set st = CreateObject("ADODB.Stream")
    st.Type = 2: st.Charset = "utf-8": st.Open
    st.LoadFromFile path
    If Err.Number <> 0 Then Exit Function
    txt = st.ReadText(-1): st.Close
    On Error GoTo 0
    Dong = Split(txt, vbLf)
    For i = LBound(Dong) To UBound(Dong)
        p = Split(Replace(Dong(i), vbCr, ""), vbTab)
        If UBound(p) >= 5 Then
            If p(0) = "H" Then
                mHx1 = SoD(p(2)): mHy1 = SoD(p(3)): mHx2 = SoD(p(4)): mHy2 = SoD(p(5))
            ElseIf p(0) = "L" And p(1) = "24" Then
                For j = 2 To UBound(p) - 1 Step 2
                    x = SoD(p(j)): y = SoD(p(j + 1))
                    If Not co Then
                        bx1 = x: bx2 = x: by1 = y: by2 = y: co = True
                    Else
                        If x < bx1 Then bx1 = x
                        If x > bx2 Then bx2 = x
                        If y < by1 Then by1 = y
                        If y > by2 Then by2 = y
                    End If
                Next j
            End If
        End If
    Next i
    If Not co Then Exit Function
    mBoxW = bx2 - bx1: mBoxH = by2 - by1
    mBoxCX = (bx1 + bx2) / 2#: mBoxCY = (by1 + by2) / 2#
    DocKhungMau = (mHx2 > mHx1)
End Function

Private Function SoD(ByVal s As String) As Double
    SoD = val(Replace(Trim$(s), ",", "."))
End Function

' Hinh bao ngoai cua thua
Private Sub BaoThua(ByVal v As clsVung, ByRef x1 As Double, ByRef y1 As Double, _
                    ByRef x2 As Double, ByRef y2 As Double)
    Dim r() As Double, i As Long
    r = v.ring
    x1 = r(0, 0): x2 = r(0, 0): y1 = r(0, 1): y2 = r(0, 1)
    For i = LBound(r, 1) To UBound(r, 1)
        If r(i, 0) < x1 Then x1 = r(i, 0)
        If r(i, 0) > x2 Then x2 = r(i, 0)
        If r(i, 1) < y1 Then y1 = r(i, 1)
        If r(i, 1) > y2 Then y2 = r(i, 1)
    Next i
End Sub

'============================================================
' Zoom view vao vung (x1,y1)-(x2,y2), chua le 8%, giu ti le khung view
'============================================================
Public Sub DC_ZoomVung(ByVal x1 As Double, ByVal y1 As Double, _
                       ByVal x2 As Double, ByVal y2 As Double)
    Dim vw As View, ex As Point3d, og As Point3d, w As Double, h As Double, asp As Double
    On Error Resume Next
    If x2 <= x1 Or y2 <= y1 Then Exit Sub
    Set vw = gViewTL
    If vw Is Nothing Then Set vw = CommandState.LastView
    If vw Is Nothing Then Set vw = ActiveDesignFile.Views(1)
    If vw Is Nothing Then Exit Sub
    ex = vw.Extents
    asp = 1#
    If ex.x > 0 Then asp = ex.y / ex.x
    w = (x2 - x1) * 1.08: h = (y2 - y1) * 1.08
    If h > w * asp Then w = h / asp Else h = w * asp
    og = vw.Origin
    og.x = (x1 + x2) / 2# - w / 2#: og.y = (y1 + y2) / 2# - h / 2#
    vw.Origin = og
    ex.x = w: ex.y = h
    vw.Extents = ex
    vw.Redraw
    Set gViewTL = Nothing
End Sub

Private Function DtMang(ByVal r As Variant) As Double
    Dim i As Long, j As Long, n0 As Long, n1 As Long, s As Double
    n0 = LBound(r, 1): n1 = UBound(r, 1)
    For i = n0 To n1
        j = i + 1: If j > n1 Then j = n0
        s = s + r(i, 0) * r(j, 1) - r(j, 0) * r(i, 1)
    Next i
    DtMang = s / 2#
End Function


'============================================================
' Nut "Xoa" canh Level ho so / Level so do: xoa MOI phan tu tren cac level
' do trong ban ve dang mo (hoi lai truoc khi xoa).
'============================================================
Public Sub DC_XoaTheoLevel(ByVal dsLv As String)
    Dim esc As ElementScanCriteria, co As Boolean
    Set esc = TaoLocLevel(dsLv, co)
    If Not co Then
        DC_ThongBao "B" & ChrW(7843) & "n v" & ChrW(7869) & " ch" & ChrW(432) & "a c" & ChrW(243) & " level n" & ChrW(224) & "o trong: " & dsLv, "X" & ChrW(243) & "a", vbExclamation
        Exit Sub
    End If
    Dim ee As ElementEnumerator, arr() As Element, n As Long, i As Long
    Set ee = ActiveModelReference.Scan(esc)
    n = DemMang(ee, arr)
    If n = 0 Then
        DC_ThongBao "Kh" & ChrW(244) & "ng c" & ChrW(243) & " " & ChrW(273) & ChrW(7889) & "i t" & ChrW(432) & ChrW(7907) & "ng n" & ChrW(224) & "o tr" & ChrW(234) & "n level " & dsLv & ".", "X" & ChrW(243) & "a"
        Exit Sub
    End If
    If DC_ThongBao("X" & ChrW(243) & "a " & n & " " & ChrW(273) & ChrW(7889) & "i t" & ChrW(432) & ChrW(7907) & "ng tr" & ChrW(234) & "n level " & dsLv & " ?", "X" & ChrW(243) & "a", vbYesNo Or vbQuestion) <> vbYes Then Exit Sub
    On Error Resume Next
    For i = 0 To n - 1
        ActiveModelReference.RemoveElement arr(i)
    Next i
    On Error GoTo 0
    RedrawAllViews
End Sub

'============================================================
' Nut "Luu file ho so": luu trich luc VUA XUAT ra file .dgn rieng.
' Chi lay phan tu tren Level ho so + Level so do, trong pham vi khung
' vua xuat. File moi lay ban ve dang mo lam seed (giu don vi, level),
' xoa sach noi dung roi chep phan tu trich luc sang.
'============================================================
Public Sub DC_LuuFileHoSo(ByVal dsHS As String, ByVal dsSD As String)
    If gTLx2 <= gTLx1 Or gTLy2 <= gTLy1 Then
        DC_ThongBao "Ch" & ChrW(432) & "a xu" & ChrW(7845) & "t tr" & ChrW(237) & "ch l" & ChrW(7909) & "c n" & ChrW(224) & "o. H" & ChrW(227) & "y b" & ChrW(7845) & "m Ch" & ChrW(7845) & "p nh" & ChrW(7853) & "n (ho" & ChrW(7863) & "c Ch" & ChrW(7885) & "n th" & ChrW(7917) & "a) tr" & ChrW(432) & ChrW(7899) & "c.", "L" & ChrW(432) & "u file h" & ChrW(7891) & " s" & ChrW(417), vbExclamation
        Exit Sub
    End If
    Dim esc As ElementScanCriteria, co As Boolean
    Set esc = TaoLocLevel(dsHS & "," & dsSD, co)
    If Not co Then
        DC_ThongBao "B" & ChrW(7843) & "n v" & ChrW(7869) & " ch" & ChrW(432) & "a c" & ChrW(243) & " level h" & ChrW(7891) & " s" & ChrW(417) & " / s" & ChrW(417) & " " & ChrW(273) & ChrW(7891) & ": " & dsHS & " ; " & dsSD, "L" & ChrW(432) & "u file h" & ChrW(7891) & " s" & ChrW(417), vbExclamation
        Exit Sub
    End If
    Dim rg As Range3d
    rg.Low.x = gTLx1: rg.Low.y = gTLy1: rg.Low.Z = -1E+20
    rg.High.x = gTLx2: rg.High.y = gTLy2: rg.High.Z = 1E+20
    esc.IncludeOnlyWithinRange rg

    Dim ee As ElementEnumerator, arr() As Element, n As Long, i As Long
    Set ee = ActiveModelReference.Scan(esc)
    n = DemMang(ee, arr)
    If n = 0 Then
        DC_ThongBao "Kh" & ChrW(244) & "ng c" & ChrW(243) & " " & ChrW(273) & ChrW(7889) & "i t" & ChrW(432) & ChrW(7907) & "ng tr" & ChrW(237) & "ch l" & ChrW(7909) & "c tr" & ChrW(234) & "n level " & dsHS & " ; " & dsSD & ".", "L" & ChrW(432) & "u file h" & ChrW(7891) & " s" & ChrW(417), vbExclamation
        Exit Sub
    End If

    ' Chon noi luu
    Dim thuMuc As String, f As String
    thuMuc = DC_DocCauHinh("LUU_TL_DIR", "")
    If Len(thuMuc) = 0 Then thuMuc = ActiveDesignFile.path
    f = DC_LuuFile("MicroStation DGN (*.dgn)|*.dgn", "Luu file ho so", thuMuc & "\" & gTLTen & ".dgn", "dgn")
    If Len(f) = 0 Then Exit Sub
    If LCase$(Right$(f, 4)) <> ".dgn" Then f = f & ".dgn"
    If LCase$(f) = LCase$(ActiveDesignFile.FullName) Then
        DC_ThongBao "Kh" & ChrW(244) & "ng " & ChrW(273) & ChrW(432) & ChrW(7907) & "c l" & ChrW(432) & "u " & ChrW(273) & ChrW(232) & " l" & ChrW(234) & "n b" & ChrW(7843) & "n v" & ChrW(7869) & " " & ChrW(273) & "ang m" & ChrW(7903) & ".", "L" & ChrW(432) & "u file h" & ChrW(7891) & " s" & ChrW(417), vbExclamation
        Exit Sub
    End If
    DC_GhiCauHinh "LUU_TL_DIR", Left$(f, InStrRev(f, "\") - 1)

    On Error Resume Next
    If Len(Dir$(f)) > 0 Then Kill f
    If Len(Dir$(f)) > 0 Then
        DC_ThongBao "Kh" & ChrW(244) & "ng ghi " & ChrW(273) & ChrW(232) & " " & ChrW(273) & ChrW(432) & ChrW(7907) & "c file (" & ChrW(273) & "ang m" & ChrW(7903) & "?): " & f, "L" & ChrW(432) & "u file h" & ChrW(7891) & " s" & ChrW(417), vbExclamation
        Exit Sub
    End If
    Err.Clear

    ' SUA 16/10/2026: NHANH - file seed RONG theo HE TOA DO (don vi + goc toa do):
    ' C:\DiaChinhVL\Mau\seed_hoso_<chu ky>.dgn. Cung he toa do -> dung lai;
    ' he toa do khac -> tao them 1 file seed moi (chi 1 lan cho he do).
    ' Truoc day chep ca ban do roi xoa tung phan tu -> rat cham.
    Dim df As DesignFile, md As ModelReference, seedF As String, ky As String
    ky = DC_ChuKySeed()
    If Len(ky) = 0 Then ky = "macdinh"
    seedF = DC_THUMUC & "\Mau\seed_hoso_" & ky & ".dgn"
    If Len(Dir$(seedF)) = 0 Then
        ShowStatus "Tao file seed cho he toa do moi (chi 1 lan)..."
        Err.Clear
        If Not TaoSeedRong(seedF) Then seedF = ""
    End If
    Err.Clear
    If Len(seedF) > 0 Then
        FileCopy seedF, f
    Else
        Application.CreateDesignFile ActiveDesignFile.FullName, f, False
    End If
    Err.Clear
    Set df = Application.OpenDesignFileForProgram(f, False)
    If df Is Nothing Or Err.Number <> 0 Then
        DC_ThongBao "Kh" & ChrW(244) & "ng t" & ChrW(7841) & "o " & ChrW(273) & ChrW(432) & ChrW(7907) & "c file: " & f & vbCrLf & Err.Description, "L" & ChrW(432) & "u file h" & ChrW(7891) & " s" & ChrW(417), vbExclamation
        Exit Sub
    End If
    Set md = df.DefaultModelReference
    If Len(seedF) = 0 Then XoaSach md          ' du phong: khong tao duoc seed
    Err.Clear

    ' Chep phan tu trich luc
    Dim nOK As Long
    For i = 0 To n - 1
        Err.Clear
        md.CopyElement arr(i)
        If Err.Number = 0 Then nOK = nOK + 1
    Next i
    Err.Clear
    df.Save
    df.Close
    On Error GoTo 0

    DC_ThongBao ChrW(272) & ChrW(227) & " l" & ChrW(432) & "u " & nOK & " " & ChrW(273) & ChrW(7889) & "i t" & ChrW(432) & ChrW(7907) & "ng tr" & ChrW(237) & "ch l" & ChrW(7909) & "c v" & ChrW(224) & "o:" & vbCrLf & f, "L" & ChrW(432) & "u file h" & ChrW(7891) & " s" & ChrW(417)
End Sub

'--- Bo loc theo danh sach so level (chi level da co trong ban ve)
' File seed rong = ban sao ban ve dang mo da xoa sach phan tu + tham chieu
Private Function TaoSeedRong(ByVal seedF As String) As Boolean
    Dim df As DesignFile
    On Error Resume Next
    If Len(Dir$(DC_THUMUC & "\Mau", vbDirectory)) = 0 Then MkDir DC_THUMUC & "\Mau"
    Err.Clear
    Application.CreateDesignFile ActiveDesignFile.FullName, seedF, False
    Set df = Application.OpenDesignFileForProgram(seedF, False)
    If df Is Nothing Or Err.Number <> 0 Then Exit Function
    XoaSach df.DefaultModelReference
    df.Save
    df.Close
    TaoSeedRong = (Err.Number = 0 And Len(Dir$(seedF)) > 0)
End Function

Private Sub XoaSach(ByVal md As ModelReference)
    Dim escX As New ElementScanCriteria, ex As ElementEnumerator, cu() As Element, nCu As Long, i As Long
    On Error Resume Next
    escX.ExcludeNonGraphical
    Set ex = md.Scan(escX)
    nCu = DemMang(ex, cu)
    For i = 0 To nCu - 1
        md.RemoveElement cu(i)
    Next i
    For i = md.Attachments.Count To 1 Step -1
        md.Attachments.Remove md.Attachments(i)
    Next i
End Sub

Private Function TaoLocLevel(ByVal dsLv As String, ByRef co As Boolean) As ElementScanCriteria
    Dim esc As New ElementScanCriteria, dS() As Long, c As Long, i As Long, lv As Level
    esc.ExcludeNonGraphical
    esc.ExcludeAllLevels
    c = DC_DsSoLevel(dsLv, dS)
    For i = 0 To c - 1
        Set lv = Nothing
        Set lv = DC_TimLevel(CStr(dS(i)))
        If Not lv Is Nothing Then esc.IncludeLevel lv: co = True
    Next i
    Set TaoLocLevel = esc
End Function

'--- Dua ket qua quet vao mang (tranh sua ban ve trong luc dang quet)
Private Function DemMang(ByVal ee As ElementEnumerator, ByRef arr() As Element) As Long
    Dim n As Long
    ReDim arr(0 To 255)
    Do While ee.MoveNext
        If n > UBound(arr) Then ReDim Preserve arr(0 To n * 2)
        Set arr(n) = ee.Current
        n = n + 1
    Loop
    DemMang = n
End Function


'============================================================
' TAT LOP BAN DO: chi chua Level ho so + Level so do (trich luc) trong
' moi view dang mo, tat ca file tham chieu (ban do nen).
' BAT LOP BAN DO: bat lai dung cac level / tham chieu vua tat
' (chua tat lan nao -> bat het moi level).
'============================================================
Public Sub DC_TatLopBanDo(ByVal dsHS As String, ByVal dsSD As String)
    Dim giu As Object, dS() As Long, c As Long, i As Long
    Set giu = CreateObject("Scripting.Dictionary")
    c = DC_DsSoLevel(dsHS & "," & dsSD, dS)
    For i = 0 To c - 1
        giu(CStr(dS(i))) = True
    Next i
    If c = 0 Then
        DC_ThongBao "Ch" & ChrW(432) & "a nh" & ChrW(7853) & "p Level h" & ChrW(7891) & " s" & ChrW(417) & " / Level s" & ChrW(417) & " " & ChrW(273) & ChrW(7891) & ".", "T" & ChrW(7855) & "t l" & ChrW(7899) & "p b" & ChrW(7843) & "n " & ChrW(273) & ChrW(7891), vbExclamation
        Exit Sub
    End If

    ' bam Tat nhieu lan lien tiep: giu danh sach cu de Bat tra lai du
    If mLvTat Is Nothing Then Set mLvTat = New Collection
    If mAttTat Is Nothing Then Set mAttTat = New Collection
    Dim vw As View, vi As Long, lv As Level
    On Error Resume Next
    For vi = 1 To 8
        Set vw = ActiveDesignFile.Views(vi)
        If Not vw Is Nothing Then
            If vw.IsOpen Then
                For Each lv In ActiveDesignFile.Levels
                    If Not giu.Exists(CStr(lv.Number)) Then
                        If lv.IsDisplayedInView(vw) Then
                            lv.IsDisplayedInView(vw) = False
                            mLvTat.Add vi & "|" & lv.Name
                        End If
                    End If
                Next lv
            End If
        End If
        Set vw = Nothing
    Next vi
    Dim att As Attachment
    For Each att In ActiveModelReference.Attachments
        If att.DisplayFlag Then
            att.DisplayFlag = False
            att.Rewrite
            mAttTat.Add att.AttachName
        End If
    Next att
    On Error GoTo 0
    RedrawAllViews
End Sub

Public Function DC_DaTatLop() As Boolean
    DC_DaTatLop = Not (mLvTat Is Nothing And mAttTat Is Nothing)
End Function

Public Sub DC_BatLopBanDo()
    Dim vw As View, vi As Long, lv As Level, i As Long, p As Long, it As String
    On Error Resume Next
    If mLvTat Is Nothing Then
        ' chua tat lan nao: bat het
        For vi = 1 To 8
            Set vw = ActiveDesignFile.Views(vi)
            If Not vw Is Nothing Then
                If vw.IsOpen Then
                    For Each lv In ActiveDesignFile.Levels
                        lv.IsDisplayedInView(vw) = True
                    Next lv
                End If
            End If
            Set vw = Nothing
        Next vi
    Else
        For i = 1 To mLvTat.Count
            it = mLvTat(i): p = InStr(it, "|")
            Set vw = ActiveDesignFile.Views(CLng(Left$(it, p - 1)))
            Set lv = ActiveDesignFile.Levels(Mid$(it, p + 1))
            If Not vw Is Nothing And Not lv Is Nothing Then lv.IsDisplayedInView(vw) = True
            Set vw = Nothing: Set lv = Nothing
        Next i
    End If
    Dim att As Attachment
    For Each att In ActiveModelReference.Attachments
        If Not att.DisplayFlag Then
            If mAttTat Is Nothing Then
                att.DisplayFlag = True: att.Rewrite
            ElseIf CoTrong(mAttTat, att.AttachName) Then
                att.DisplayFlag = True: att.Rewrite
            End If
        End If
    Next att
    On Error GoTo 0
    Set mLvTat = Nothing: Set mAttTat = Nothing
    RedrawAllViews
End Sub

Private Function CoTrong(ByVal col As Collection, ByVal s As String) As Boolean
    Dim i As Long
    For i = 1 To col.Count
        If col(i) = s Then CoTrong = True: Exit Function
    Next i
End Function

'============================================================
' Dung chung cho tach/hop thua (modTachHop)
'============================================================
Public Function DC_TyLeTuDong(ByVal v As clsVung, ByVal mauPath As String) As Double
    DC_TyLeTuDong = TyLeTuDong(v, mauPath)
End Function

' Pham vi khung mau sau khi dat (o so do level 24 tai (cx, cy))
Public Function DC_PhamViKhung(ByVal mauPath As String, ByVal tyLe As Double, _
                               ByVal cx As Double, ByVal cy As Double, _
                               ByRef x1 As Double, ByRef y1 As Double, _
                               ByRef x2 As Double, ByRef y2 As Double) As Boolean
    If Not DocKhungMau(mauPath) Then Exit Function
    x1 = cx + (mHx1 - mBoxCX) * tyLe / 20000#
    x2 = cx + (mHx2 - mBoxCX) * tyLe / 20000#
    y1 = cy + (mHy1 - mBoxCY) * tyLe / 20000#
    y2 = cy + (mHy2 - mBoxCY) * tyLe / 20000#
    DC_PhamViKhung = (x2 > x1)
End Function

' Doc nhieu thua tu CSDL: "12,13" / "12+13" / "12 13"
Public Function DC_LayThuaCSDL(ByVal csdlPath As String, ByVal dsSo As String, _
                               ByRef Loi As String) As Collection
    Dim vungs As Collection, a() As String, i As Long, j As Long, v As clsVung, kq As New Collection
    Dim t As String, gap As Boolean
    Set vungs = MoCSDL(csdlPath)
    If vungs.Count = 0 Then Loi = "CSDL r" & ChrW(7895) & "ng / kh" & ChrW(244) & "ng " & ChrW(273) & ChrW(7885) & "c " & ChrW(273) & ChrW(432) & ChrW(7907) & "c: " & csdlPath: Exit Function
    t = Replace(Replace(Replace(dsSo, "+", ","), ";", ","), " ", ",")
    a = Split(t, ",")
    For i = 0 To UBound(a)
        If Len(Trim$(a(i))) > 0 Then
            gap = False
            For j = 1 To vungs.Count
                Set v = vungs.Item(j)
                If Trim$(v.soThua) = Trim$(a(i)) Then kq.Add v: gap = True: Exit For
            Next j
            If Not gap Then Loi = "Kh" & ChrW(244) & "ng t" & ChrW(236) & "m th" & ChrW(7845) & "y th" & ChrW(7917) & "a s" & ChrW(7889) & " " & Trim$(a(i)) & " trong CSDL.": Exit Function
        End If
    Next i
    If kq.Count = 0 Then Loi = "Ch" & ChrW(432) & "a nh" & ChrW(7853) & "p s" & ChrW(7889) & " th" & ChrW(7917) & "a.": Exit Function
    Set DC_LayThuaCSDL = kq
End Function

Attribute VB_Name = "modNhan"
Option Explicit

'============================================================
' modNhan - Ve nhan chu len ban do (MicroStation V8i)
' Port dan tu ve_nhan_thua / tao_text (Python).
'
' Tao chu bang: CreateTextElement1(Nothing, chuoi, origin, Matrix3dIdentity)
' Dat co chu / can le qua ActiveSettings.TextStyle truoc khi tao.
'============================================================


'============================================================
' VE MOT DOAN CHU tai (x, y)
'   cao   : chieu cao chu (don vi ban ve)
'   color : -1 = giu mau active
'   justif: -1 = can giua giua (center-center)
'============================================================
Public Sub VeText(ByVal x As Double, ByVal y As Double, ByVal noiDung As String, _
                  ByVal cao As Double, Optional ByVal color As Long = -1, _
                  Optional ByVal justif As Long = -1)
    If Len(noiDung) = 0 Then Exit Sub

    On Error Resume Next
    ActiveSettings.TextStyle.Height = cao
    ActiveSettings.TextStyle.Width = cao
    If justif < 0 Then
        ActiveSettings.TextStyle.Justification = msdTextJustificationCenterCenter
    Else
        ActiveSettings.TextStyle.Justification = justif
    End If
    On Error GoTo 0

    Dim OText As TextElement
    Set OText = CreateTextElement1(Nothing, noiDung, Point3dFromXYZ(x, y, 0#), Matrix3dIdentity)
    If color >= 0 Then OText.color = color
    On Error Resume Next
    OText.LineWeight = 0
    On Error GoTo 0
    ActiveModelReference.AddElement OText
End Sub


'============================================================
' VE NHAN PHAN SO: dong tren / gach ngang / dong duoi
'   (giong kieu "102 / 3509.2" tren ban do dia chinh)
'============================================================
Public Sub VeNhanPhanSo(ByVal x As Double, ByVal y As Double, _
                        ByVal tren As String, ByVal duoi As String, _
                        ByVal cao As Double, Optional ByVal color As Long = -1)
    Dim w As Double, wt As Double, wd As Double
    ' Uoc luong be rong de ve gach ngang (0.6 * cao * so ky tu)
    wt = Len(tren) * cao * 0.6
    wd = Len(duoi) * cao * 0.6
    w = wt
    If wd > w Then w = wd
    If w <= 0 Then w = cao

    If Len(tren) > 0 Then VeText x, y + cao * 0.75, tren, cao, color
    If Len(duoi) > 0 Then VeText x, y - cao * 0.75, duoi, cao, color
    ' gach ngang giua hai dong
    VeLine x - w / 2#, y, x + w / 2#, y, color
End Sub


'============================================================
' Noi dung nhan tu mot truong (giong _noi_dung_field Python)
'============================================================
Public Function NoiDungTruong(ByVal v As clsVung, ByVal truong As String) As String
    Select Case truong
        Case "so_thua":  NoiDungTruong = v.soThua
        Case "loai_dat": NoiDungTruong = v.loaiDat
        Case "ten_chu":  NoiDungTruong = v.TenChu
        Case "dt":       NoiDungTruong = Format$(Round(v.dt, 1), "0.0")
        Case Else:       NoiDungTruong = ""
    End Select
End Function


'============================================================
' Uoc luong co chu tu bounding box (nho hon dau danh dau)
'============================================================
Private Function CoChuUocLuong(ByVal minX As Double, ByVal minY As Double, _
                               ByVal maxX As Double, ByVal maxY As Double) As Double
    Dim s As Double
    s = ((maxX - minX) + (maxY - minY)) / 2# / 1500#
    If s <= 0# Then s = 1#
    CoChuUocLuong = s
End Function

Private Function TenLevelActive() As String
    On Error Resume Next
    TenLevelActive = ActiveSettings.Level.Name
    On Error GoTo 0
End Function


'============================================================
' LENH CHAY DUOC: GAN NHAN DIEN TICH tai tam moi thua
'============================================================
Public Sub DC_GanNhanDienTich()
    Dim lvName As String, snapStr As String, snap As Double
    lvName = InputBox("Nhap TEN level chua ranh thua." & vbCrLf & _
                      "(De trong = doc tat ca line/linestring)", _
                      "Gan nhan dien tich", TenLevelActive())
    snapStr = InputBox("Dung sai noi diem (snap):", "Gan nhan dien tich", "0.05")
    If snapStr = "" Then Exit Sub
    snap = val(snapStr)
    If snap <= 0 Then snap = 0.05

    Dim minX As Double, minY As Double, maxX As Double, maxY As Double
    Dim segs As Collection
    Set segs = LayCacDoan(snap, lvName, minX, minY, maxX, maxY)
    If segs.Count = 0 Then
        MsgBox "Khong doc duoc doan ranh nao.", vbExclamation, "Gan nhan dien tich"
        Exit Sub
    End If

    ' Hoi co chu
    Dim caoStr As String, cao As Double
    cao = CoChuUocLuong(minX, minY, maxX, maxY)
    caoStr = InputBox("Co chu (chieu cao, don vi ban ve):", _
                      "Gan nhan dien tich", Format$(cao, "0.###"))
    If caoStr <> "" Then cao = val(caoStr)
    If cao <= 0 Then cao = 1

    Dim soTia As Long
    Dim vungs As Collection
    Set vungs = GhepVung(segs, snap, soTia)

    Dim i As Long, v As clsVung, tong As Double
    tong = 0#
    For i = 1 To vungs.Count
        Set v = vungs.Item(i)
        VeText v.cx, v.cy, Format$(Round(v.dt, 1), "0.0"), cao, 2   ' mau 2 cho de thay
        tong = tong + v.dt
    Next i

    MsgBox "So thua gan nhan: " & vungs.Count & vbCrLf & _
           "Tong dien tich: " & Format$(tong, "#,##0.0"), _
           vbInformation, "Gan nhan dien tich"
End Sub

Attribute VB_Name = "modPhanNhan"
'============================================================
' modPhanNhan - PHAN NHAN THEO THUA (SUA 07/11)
'   Moi vung thua (ghep tu lop ranh): gom chu tren cac lop nguon, nhan dang
'   so thua / loai dat / dien tich (ke ca nhan gop "LUC 2601 / 145", "593/",
'   "/82", "1225/72/ONT"...), tach thanh chu rieng va dua ve lop dung
'   (mac dinh 13 / 2 / 4). Chu goc -> lop luu (mac dinh 60).
'   Quy tac: 1 so nguyen dung rieng = so thua; 2 so nguyen chong nhau
'   = tren so thua, duoi dien tich; so sau dau "/" = dien tich.
'   Vung khong chac chan -> KHONG sua, dua vao KV_DsLoi de nguoi dung xem.
'   Form: nut "Phan nhan theo thua" tren frmKiemVung.
'============================================================
Option Explicit

' du lieu chu
Private pEl As Collection          ' Element goc
Private pS() As String             ' noi dung
Private px() As Double, py() As Double, pH() As Double, pDX() As Double, pDY() As Double
Private pVung() As Long            ' chi so vung (0 = ngoai)
Private pNP() As Long              ' so phan (0 = la / bo qua)
Private pVai() As String           ' vai tro tung phan "S"/"L"/"D"/"B" noi bang "|"
Private pTok() As String           ' noi dung tung phan noi bang "|"
Private pPos() As String           ' vi tri ky tu tung phan noi bang "|"
Private pRac() As Boolean          ' chu chi gom "/" (rac)
Private pLa() As Boolean           ' chu co so nhung khong hieu -> vung nghi ngo
Private pN As Long

Public Function PN_Chay(ByVal ranhCSV As String, ByVal nguonCSV As String, _
                        ByVal lvSo As String, ByVal lvLD As String, ByVal lvDT As String, _
                        ByVal lvLuu As String, ByVal snap As Double, ByVal chiaGiao As Boolean, _
                        ByRef tomTat As String) As Long
    Dim td As String
    td = "Ph" & ChrW(226) & "n nh" & ChrW(227) & "n theo th" & ChrW(7917) & "a"
    Set KV_DsLoi = New Collection
    tomTat = ""
    If snap <= 0 Then snap = 0.001

    ' --- 1. vung thua
    Dim segs As Collection, vungs As Collection, tia As Long
    Dim minX As Double, minY As Double, maxX As Double, maxY As Double
    ShowStatus "Phan nhan: doc ranh ..."
    Set segs = LayDoanNhieuLevel(ranhCSV, snap, minX, minY, maxX, maxY)
    If segs Is Nothing Then tomTat = "Kh" & ChrW(244) & "ng " & ChrW(273) & ChrW(7885) & "c " & ChrW(273) & ChrW(432) & ChrW(7907) & "c ranh l" & ChrW(7899) & "p " & ranhCSV: Exit Function
    If segs.Count = 0 Then tomTat = "Kh" & ChrW(244) & "ng " & ChrW(273) & ChrW(7885) & "c " & ChrW(273) & ChrW(432) & ChrW(7907) & "c ranh l" & ChrW(7899) & "p " & ranhCSV: Exit Function
    If chiaGiao Then Set segs = NoiDoanGiao(segs, snap)
    ShowStatus "Phan nhan: ghep vung ..."
    Set vungs = GhepVung(segs, snap, tia)
    If vungs Is Nothing Then tomTat = "Kh" & ChrW(244) & "ng gh" & ChrW(233) & "p " & ChrW(273) & ChrW(432) & ChrW(7907) & "c v" & ChrW(249) & "ng th" & ChrW(7917) & "a.": Exit Function
    If vungs.Count = 0 Then tomTat = "Kh" & ChrW(244) & "ng gh" & ChrW(233) & "p " & ChrW(273) & ChrW(432) & ChrW(7907) & "c v" & ChrW(249) & "ng th" & ChrW(7917) & "a.": Exit Function
    Dim nV As Long, i As Long, j As Long, k As Long, rg() As Double
    nV = vungs.Count
    Dim bx1() As Double, by1() As Double, bx2() As Double, by2() As Double
    ReDim bx1(1 To nV): ReDim by1(1 To nV): ReDim bx2(1 To nV): ReDim by2(1 To nV)
    For i = 1 To nV
        rg = vungs.Item(i).ring
        BaoRing rg, bx1(i), by1(i), bx2(i), by2(i)
    Next i

    ' --- 2. lop nguon
    Dim arr() As String, lvN() As Long, nL As Long, o As Level
    arr = Split(nguonCSV, ",")
    ReDim lvN(0 To UBound(arr) + 1)
    For i = 0 To UBound(arr)
        If Len(Trim$(arr(i))) > 0 Then
            Set o = DC_TimLevel(Trim$(arr(i)))
            If Not o Is Nothing Then lvN(nL) = o.Number: nL = nL + 1
        End If
    Next i
    If nL = 0 Then tomTat = "Kh" & ChrW(244) & "ng t" & ChrW(236) & "m th" & ChrW(7845) & "y l" & ChrW(7899) & "p ngu" & ChrW(7891) & "n " & nguonCSV: Exit Function

    ' --- 3. doc chu
    ShowStatus "Phan nhan: doc chu ..."
    Set pEl = New Collection: pN = 0
    ReDim pS(1 To 1000): ReDim px(1 To 1000): ReDim py(1 To 1000): ReDim pH(1 To 1000)
    ReDim pDX(1 To 1000): ReDim pDY(1 To 1000)
    Dim esc As ElementScanCriteria, ee As ElementEnumerator, el As Element, c As Element, lvE As Long, ok As Boolean
    Dim s As String, rot As Matrix3d, ddx As Double, ddy As Double, L As Double
    Set esc = New ElementScanCriteria
    esc.ExcludeAllTypes
    esc.IncludeType msdElementTypeText
    esc.IncludeType msdElementTypeTextNode
    Set ee = ActiveModelReference.Scan(esc)
    On Error Resume Next
    Do While ee.MoveNext
        Set el = ee.Current
        lvE = el.Level.Number
        ok = False
        For k = 0 To nL - 1
            If lvE = lvN(k) Then ok = True: Exit For
        Next k
        If ok Then
            Set c = PN_ChuDon(el)
            If Not c Is Nothing Then
                s = c.AsTextElement.Text
                If Len(Trim$(s)) > 0 Then
                    pN = pN + 1
                    If pN > UBound(pS) Then
                        ReDim Preserve pS(1 To pN * 2): ReDim Preserve px(1 To pN * 2): ReDim Preserve py(1 To pN * 2)
                        ReDim Preserve pH(1 To pN * 2): ReDim Preserve pDX(1 To pN * 2): ReDim Preserve pDY(1 To pN * 2)
                    End If
                    pEl.Add el
                    pS(pN) = s
                    px(pN) = (el.Range.Low.x + el.Range.High.x) / 2#
                    py(pN) = (el.Range.Low.y + el.Range.High.y) / 2#
                    pH(pN) = c.AsTextElement.TextStyle.Height
                    rot = c.AsTextElement.Rotation
                    ddx = rot.RowX.x: ddy = rot.RowY.x
                    If Err.Number <> 0 Then ddx = 1#: ddy = 0#: Err.Clear
                    L = Sqr(ddx * ddx + ddy * ddy)
                    If L <= 0# Then ddx = 1#: ddy = 0#: L = 1#
                    pDX(pN) = ddx / L: pDY(pN) = ddy / L
                End If
            End If
        End If
        Err.Clear
    Loop
    On Error GoTo 0
    If pN = 0 Then tomTat = "Kh" & ChrW(244) & "ng c" & ChrW(243) & " ch" & ChrW(7919) & " n" & ChrW(224) & "o tr" & ChrW(234) & "n l" & ChrW(7899) & "p " & nguonCSV: Exit Function

    ' --- 4. phan tich tung chu + gan vung
    ShowStatus "Phan nhan: phan tich " & pN & " chu ..."
    ReDim pVung(1 To pN): ReDim pNP(1 To pN): ReDim pVai(1 To pN): ReDim pTok(1 To pN): ReDim pPos(1 To pN)
    ReDim pRac(1 To pN): ReDim pLa(1 To pN)
    For j = 1 To pN
        PN_PhanTich j
        For i = 1 To nV
            If px(j) >= bx1(i) And px(j) <= bx2(i) And py(j) >= by1(i) And py(j) <= by2(i) Then
                If PN_TrongVung(vungs.Item(i), px(j), py(j)) Then pVung(j) = i: Exit For
            End If
        Next i
        If j Mod 200 = 0 Then DoEvents
    Next j

    ' --- 5. quyet dinh tung vung
    ShowStatus "Phan nhan: quyet dinh ..."
    Dim dsChu() As String, nVungSua As Long, nNghi As Long, ly As String, ghi As String
    ReDim dsChu(1 To nV)
    For j = 1 To pN
        If pVung(j) > 0 Then
            If Len(dsChu(pVung(j))) > 0 Then dsChu(pVung(j)) = dsChu(pVung(j)) & ","
            dsChu(pVung(j)) = dsChu(pVung(j)) & j
        End If
    Next j
    Dim okV() As Boolean
    ReDim okV(1 To nV)
    For i = 1 To nV
        If Len(dsChu(i)) > 0 Then
            ly = PN_QuyetDinh(dsChu(i), ghi)
            If Len(ly) = 0 Then
                If Len(ghi) > 0 Then okV(i) = True: nVungSua = nVungSua + 1
            Else
                nNghi = nNghi + 1
                KV_DsLoi.Add Array(vungs.Item(i), ly, ghi)
            End If
        End If
    Next i

    ' --- 6. xac nhan + thuc hien
    Dim msg As String
    msg = "S" & ChrW(7869) & " s" & ChrW(7855) & "p x" & ChrW(7871) & "p nh" & ChrW(227) & "n cho " & nVungSua & " v" & ChrW(249) & "ng th" & ChrW(7917) & "a (s" & ChrW(7889) & " th" & ChrW(7917) & "a " & ChrW(8594) & " l" & ChrW(7899) & "p " & lvSo & ", lo" & ChrW(7841) & "i " & ChrW(273) & ChrW(7845) & "t " & ChrW(8594) & " l" & ChrW(7899) & "p " & lvLD & ", di" & ChrW(7879) & "n t" & ChrW(237) & "ch " & ChrW(8594) & " l" & ChrW(7899) & "p " & lvDT & ")." & vbCrLf & _
          "Ch" & ChrW(7919) & " g" & ChrW(7889) & "c b" & ChrW(7883) & " t" & ChrW(225) & "ch/thay s" & ChrW(7869) & " chuy" & ChrW(7875) & "n sang l" & ChrW(7899) & "p " & lvLuu & " (kh" & ChrW(244) & "ng x" & ChrW(243) & "a)." & vbCrLf & _
          nNghi & " v" & ChrW(249) & "ng kh" & ChrW(244) & "ng ch" & ChrW(7855) & "c ch" & ChrW(7855) & "n s" & ChrW(7869) & " KH" & ChrW(212) & "NG s" & ChrW(7917) & "a, ch" & ChrW(7881) & " li" & ChrW(7879) & "t k" & ChrW(234) & " " & ChrW(273) & ChrW(7875) & " b" & ChrW(7841) & "n xem." & vbCrLf & vbCrLf & "Th" & ChrW(7921) & "c hi" & ChrW(7879) & "n?"
    ShowStatus ""
    If nVungSua = 0 Then
        tomTat = "Kh" & ChrW(244) & "ng c" & ChrW(243) & " v" & ChrW(249) & "ng n" & ChrW(224) & "o s" & ChrW(7917) & "a t" & ChrW(7921) & " " & ChrW(273) & ChrW(7897) & "ng " & ChrW(273) & ChrW(432) & ChrW(7907) & "c. " & nNghi & " v" & ChrW(249) & "ng c" & ChrW(7847) & "n xem tay (danh s" & ChrW(225) & "ch b" & ChrW(234) & "n d" & ChrW(432) & ChrW(7899) & "i)."
        Exit Function
    End If
    If DC_ThongBao(msg, td, vbYesNo + vbQuestion) <> vbYes Then
        tomTat = ChrW(272) & ChrW(227) & " h" & ChrW(7911) & "y. " & nNghi & " v" & ChrW(249) & "ng c" & ChrW(7847) & "n xem tay (danh s" & ChrW(225) & "ch b" & ChrW(234) & "n d" & ChrW(432) & ChrW(7899) & "i)."
        Exit Function
    End If

    Dim oSo As Level, oLD As Level, oDT As Level, oLuu As Level
    Set oSo = PN_Lop(lvSo): Set oLD = PN_Lop(lvLD): Set oDT = PN_Lop(lvDT): Set oLuu = PN_Lop(lvLuu)
    If oSo Is Nothing Or oLD Is Nothing Or oDT Is Nothing Or oLuu Is Nothing Then
        tomTat = "Kh" & ChrW(244) & "ng t" & ChrW(7841) & "o/t" & ChrW(236) & "m " & ChrW(273) & ChrW(432) & ChrW(7907) & "c l" & ChrW(7899) & "p " & ChrW(273) & ChrW(237) & "ch (" & lvSo & ", " & lvLD & ", " & lvDT & ", " & lvLuu & ").": Exit Function
    End If
    ShowStatus "Phan nhan: dang sua ..."
    Dim nMoi As Long, nDoi As Long, nLuu As Long
    For j = 1 To pN
        If pVung(j) > 0 Then
            If okV(pVung(j)) Then PN_ThucHien j, oSo, oLD, oDT, oLuu, nMoi, nDoi, nLuu
        End If
        If j Mod 200 = 0 Then DoEvents
    Next j
    ShowStatus ""
    tomTat = ChrW(272) & ChrW(227) & " s" & ChrW(7855) & "p x" & ChrW(7871) & "p " & nVungSua & " v" & ChrW(249) & "ng: " & ChrW(273) & ChrW(7893) & "i l" & ChrW(7899) & "p " & nDoi & " ch" & ChrW(7919) & ", t" & ChrW(7841) & "o " & nMoi & " ch" & ChrW(7919) & " t" & ChrW(225) & "ch, chuy" & ChrW(7875) & "n " & nLuu & " ch" & ChrW(7919) & " g" & ChrW(7889) & "c sang l" & ChrW(7899) & "p " & lvLuu & "." & vbCrLf & _
             nNghi & " v" & ChrW(249) & "ng c" & ChrW(7847) & "n xem tay (b" & ChrW(7845) & "m t" & ChrW(7915) & "ng d" & ChrW(242) & "ng " & ChrW(273) & ChrW(7875) & " ph" & ChrW(243) & "ng t" & ChrW(7899) & "i). Sau " & ChrW(273) & ChrW(243) & " b" & ChrW(7845) & "m Ki" & ChrW(7875) & "m tra."
    PN_Chay = nVungSua
End Function

' Text -> chinh no ; text node 1 dong -> chu con ; con lai Nothing
Private Function PN_ChuDon(ByVal el As Element) As Element
    Dim sb As ElementEnumerator, dem As Long, c As Element
    On Error Resume Next
    If el.Type = msdElementTypeText Then Set PN_ChuDon = el: Exit Function
    Set sb = el.AsTextNodeElement.GetSubElements
    If sb Is Nothing Then Exit Function
    Do While sb.MoveNext
        If sb.Current.Type = msdElementTypeText Then dem = dem + 1: Set c = sb.Current
    Loop
    If dem = 1 Then Set PN_ChuDon = c
End Function

Private Function PN_Lop(ByVal t As String) As Level
    If IsNumeric(Trim$(t)) Then
        Set PN_Lop = DC_LevelTheoSo(CLng(val(t)))
    Else
        Set PN_Lop = DC_TimLevel(t)
    End If
End Function

Private Function PN_TrongVung(ByVal v As clsVung, ByVal x As Double, ByVal y As Double) As Boolean
    Dim rg() As Double, k As Long
    rg = v.ring
    If Not DiemTrongPolygon(rg, x, y) Then Exit Function
    For k = 1 To v.dao.Count
        rg = v.dao.Item(k)
        If DiemTrongPolygon(rg, x, y) Then Exit Function
    Next k
    PN_TrongVung = True
End Function

' Loai ky tu: 1 chu IN HOA / +, 2 chu so / , . (trong so), 3 dau /, 0 khoang trang, 9 khac
Private Function PN_LoaiKT(ByVal ch As String) As Long
    Dim c As Long
    c = AscW(ch) And &HFFFF&
    If (c >= 65 And c <= 90) Or c = 43 Then
        PN_LoaiKT = 1
    ElseIf c >= 48 And c <= 57 Then
        PN_LoaiKT = 2
    ElseIf c = 47 Then
        PN_LoaiKT = 3
    ElseIf c <= 32 Then
        PN_LoaiKT = 0
    ElseIf c = 44 Or c = 46 Then
        PN_LoaiKT = 4
    Else
        PN_LoaiKT = 9
    End If
End Function

' Phan tich chu j -> cac phan (vai tro, noi dung, vi tri)
Private Sub PN_PhanTich(ByVal j As Long)
    Dim s As String, i As Long, ch As String, lk As Long, cur As Long, tok As String, bd As Long
    Dim tk() As String, tp() As Long, tb() As Long, nt As Long
    ReDim tk(1 To 30): ReDim tp(1 To 30): ReDim tb(1 To 30)
    s = pS(j)
    ' --- tach token: chu (1), so (2, cho , . o giua), "/" (3)
    cur = 0: tok = ""
    For i = 1 To Len(s) + 1
        If i <= Len(s) Then ch = Mid$(s, i, 1): lk = PN_LoaiKT(ch) Else ch = "": lk = 0
        If lk = 4 Then
            If cur = 2 Then lk = 2 Else lk = 9               ' dau , . chi hop le ngay sau chu so
        End If
        If lk = 9 Then
            ' chu thuong / co dau / ma TCVN (ghi chu, ten duong...) -> bo qua chu nay
            ' ky tu la khac ( "(", "-", ...) ma co so -> vung nghi ngo
            pLa(j) = (PN_CoSo(s) And Not PN_CoChuThuong(s))
            pNP(j) = 0
            Exit Sub
        End If
        If lk <> cur Or lk = 3 Then
            If cur <> 0 And Len(tok) > 0 And nt < 30 Then nt = nt + 1: tk(nt) = tok: tp(nt) = cur: tb(nt) = bd
            tok = "": bd = i
        End If
        If lk <> 0 Then tok = tok & ch
        cur = lk
    Next i
    If nt = 0 Then Exit Sub
    ' so: phan biet nguyen (I) / thap phan (D); bo dau , . o cuoi
    Dim nL As Long, nS As Long, sauGach As Boolean, idx(1 To 3) As Long, nNum As Long, gachSau(1 To 3) As Boolean, kieu(1 To 3) As String
    Dim iL As Long, t As String
    For i = 1 To nt
        Select Case tp(i)
            Case 1
                If Len(tk(i)) < 2 Or Len(tk(i)) > 12 Then pLa(j) = PN_CoSo(s): Exit Sub
                nL = nL + 1: iL = i
            Case 2
                t = tk(i)
                Do While Len(t) > 0 And (Right$(t, 1) = "," Or Right$(t, 1) = ".")
                    t = Left$(t, Len(t) - 1)
                Loop
                tk(i) = t
                nNum = nNum + 1
                If nNum > 3 Then pLa(j) = True: Exit Sub
                idx(nNum) = i
                ' so dung sau "/": so dau tien chi tinh khi truoc no KHONG co ma loai dat
                If nNum = 1 Then gachSau(1) = sauGach And (nL = 0) Else gachSau(nNum) = sauGach
                sauGach = False
                If InStr(t, ",") > 0 Or InStr(t, ".") > 0 Then kieu(nNum) = "D" Else kieu(nNum) = "I"
            Case 3
                nS = nS + 1: sauGach = True
        End Select
    Next i
    If nL > 1 Then pLa(j) = True: Exit Sub
    Dim vai As String, tok2 As String, pos As String, n As Long
    If nNum = 0 Then
        If nL = 1 Then
            n = 1: vai = "L": tok2 = tk(iL): pos = CStr(tb(iL))
        ElseIf nS > 0 Then
            pRac(j) = True
        End If
    ElseIf nNum = 1 Then
        Dim r As String
        If kieu(1) = "D" Or gachSau(1) Then
            r = "D"
        ElseIf nL = 1 Or nS > 0 Then
            r = "S"                                   ' "LUC 123", "123/", "123 /"
        Else
            r = "B"                                   ' so nguyen dung rieng
        End If
        n = 1: vai = r: tok2 = tk(idx(1)): pos = CStr(tb(idx(1)))
        If nL = 1 Then n = 2: vai = "L|" & vai: tok2 = tk(iL) & "|" & tok2: pos = tb(iL) & "|" & pos
    ElseIf nNum = 2 Then
        ' so 1 = so thua (nguyen, khong sau "/"), so 2 = dien tich (sau "/" hoac thap phan)
        If kieu(1) <> "I" Or gachSau(1) Then pLa(j) = True: Exit Sub
        If Not (gachSau(2) Or kieu(2) = "D") Then pLa(j) = True: Exit Sub
        n = 2: vai = "S|D": tok2 = tk(idx(1)) & "|" & tk(idx(2)): pos = tb(idx(1)) & "|" & tb(idx(2))
        If nL = 1 Then n = 3: vai = "L|" & vai: tok2 = tk(iL) & "|" & tok2: pos = tb(iL) & "|" & pos
    Else
        pLa(j) = True: Exit Sub
    End If
    pNP(j) = n: pVai(j) = vai: pTok(j) = tok2: pPos(j) = pos
End Sub

Private Function PN_CoSo(ByVal s As String) As Boolean
    Dim i As Long, c As Long
    For i = 1 To Len(s)
        c = AscW(Mid$(s, i, 1))
        If c >= 48 And c <= 57 Then PN_CoSo = True: Exit Function
    Next i
End Function

' Quyet dinh 1 vung. Tra ve "" neu sua duoc (ghi = danh sach chu), nguoc lai ly do (ghi = noi dung chu)
Private Function PN_QuyetDinh(ByVal dS As String, ByRef ghi As String) As String
    Dim a() As String, i As Long, j As Long, k As Long, v() As String, nS As Long, nL As Long, nD As Long
    Dim bj(1 To 3) As Long, bk(1 To 3) As Long, nb As Long, la As Boolean, noi As String
    a = Split(dS, ",")
    ghi = ""
    For i = 0 To UBound(a)
        j = CLng(a(i))
        noi = noi & IIf(Len(noi) > 0, "; ", "") & Trim$(pS(j))
        If pLa(j) Then la = True
        If pNP(j) > 0 Then
            v = Split(pVai(j), "|")
            For k = 0 To UBound(v)
                Select Case v(k)
                    Case "S": nS = nS + 1
                    Case "L": nL = nL + 1
                    Case "D": nD = nD + 1
                    Case "B"
                        nb = nb + 1
                        If nb <= 3 Then bj(nb) = j: bk(nb) = k
                End Select
            Next k
        End If
    Next i
    ghi = noi
    If la Then PN_QuyetDinh = "C" & ChrW(243) & " nh" & ChrW(227) & "n l" & ChrW(7841) & " (kh" & ChrW(244) & "ng t" & ChrW(225) & "ch " & ChrW(273) & ChrW(432) & ChrW(7907) & "c ch" & ChrW(7855) & "c ch" & ChrW(7855) & "n)": Exit Function
    ' so nguyen dung rieng
    If nb = 1 Then
        If nS = 0 Then
            PN_DatVai bj(1), bk(1), "S": nS = 1
        ElseIf nD = 0 Then
            PN_DatVai bj(1), bk(1), "D": nD = 1
        Else
            PN_QuyetDinh = "Th" & ChrW(7915) & "a 1 s" & ChrW(7889) & " kh" & ChrW(244) & "ng r" & ChrW(245) & " l" & ChrW(224) & " s" & ChrW(7889) & " th" & ChrW(7917) & "a hay di" & ChrW(7879) & "n t" & ChrW(237) & "ch": Exit Function
        End If
    ElseIf nb = 2 Then
        If nS = 0 And nD = 0 Then
            ' 2 so chong nhau: tren = so thua, duoi = dien tich
            Dim u1 As Double, u2 As Double, j1 As Long, j2 As Long, doc As Double, ngang As Double, hh As Double
            j1 = bj(1): j2 = bj(2)
            u1 = -pDY(j1) * px(j1) + pDX(j1) * py(j1)
            u2 = -pDY(j1) * px(j2) + pDX(j1) * py(j2)
            ngang = Abs(pDX(j1) * (px(j2) - px(j1)) + pDY(j1) * (py(j2) - py(j1)))
            doc = Abs(u2 - u1)
            hh = pH(j1): If pH(j2) > hh Then hh = pH(j2)
            Dim a1 As Double, a2 As Double
            a1 = pDX(j1) * px(j1) + pDY(j1) * py(j1)
            a2 = pDX(j1) * px(j2) + pDY(j1) * py(j2)
            If doc >= hh * 0.6 And doc <= hh * 4# And ngang <= hh * 4# Then
                ' chong tren/duoi: tren = so thua
                If u1 > u2 Then
                    PN_DatVai j1, bk(1), "S": PN_DatVai j2, bk(2), "D"
                Else
                    PN_DatVai j2, bk(2), "S": PN_DatVai j1, bk(1), "D"
                End If
            ElseIf doc < hh * 0.6 And ngang <= hh * 8# Then
                ' cung 1 dong: trai = so thua, phai = dien tich
                If a1 < a2 Then
                    PN_DatVai j1, bk(1), "S": PN_DatVai j2, bk(2), "D"
                Else
                    PN_DatVai j2, bk(2), "S": PN_DatVai j1, bk(1), "D"
                End If
            Else
                PN_QuyetDinh = "2 s" & ChrW(7889) & " r" & ChrW(7901) & "i xa nhau - c" & ChrW(243) & " th" & ChrW(7875) & " 2 th" & ChrW(7917) & "a chung 1 v" & ChrW(249) & "ng (thi" & ChrW(7871) & "u ranh)": Exit Function
            End If
            nS = 1: nD = 1
        Else
            PN_QuyetDinh = "C" & ChrW(243) & " 2 s" & ChrW(7889) & " r" & ChrW(7901) & "i kh" & ChrW(244) & "ng x" & ChrW(225) & "c " & ChrW(273) & ChrW(7883) & "nh " & ChrW(273) & ChrW(432) & ChrW(7907) & "c": Exit Function
        End If
    ElseIf nb > 2 Then
        PN_QuyetDinh = nb & " s" & ChrW(7889) & " r" & ChrW(7901) & "i - c" & ChrW(243) & " th" & ChrW(7875) & " nhi" & ChrW(7873) & "u th" & ChrW(7917) & "a chung 1 v" & ChrW(249) & "ng (thi" & ChrW(7871) & "u ranh)": Exit Function
    End If
    If nS > 1 Then PN_QuyetDinh = nS & " s" & ChrW(7889) & " th" & ChrW(7917) & "a trong 1 v" & ChrW(249) & "ng (thi" & ChrW(7871) & "u ranh ho" & ChrW(7863) & "c nh" & ChrW(227) & "n tr" & ChrW(249) & "ng)": Exit Function
    If nL > 1 Then PN_QuyetDinh = nL & " lo" & ChrW(7841) & "i " & ChrW(273) & ChrW(7845) & "t trong 1 v" & ChrW(249) & "ng": Exit Function
    If nD > 1 Then PN_QuyetDinh = nD & " di" & ChrW(7879) & "n t" & ChrW(237) & "ch trong 1 v" & ChrW(249) & "ng": Exit Function
    If nS + nL + nD = 0 Then ghi = ""
End Function

Private Sub PN_DatVai(ByVal j As Long, ByVal k As Long, ByVal r As String)
    Dim v() As String, i As Long, s As String
    v = Split(pVai(j), "|")
    v(k) = r
    For i = 0 To UBound(v)
        s = s & IIf(i > 0, "|", "") & v(i)
    Next i
    pVai(j) = s
End Sub

' Sua 1 chu: 1 phan & noi dung trung khit -> doi lop ; con lai -> tao chu tach + chuyen goc sang lop luu
Private Sub PN_ThucHien(ByVal j As Long, ByVal oSo As Level, ByVal oLD As Level, ByVal oDT As Level, ByVal oLuu As Level, _
                        ByRef nMoi As Long, ByRef nDoi As Long, ByRef nLuu As Long)
    Dim el As Element, c As Element, te As TextElement, v() As String, tk() As String, vt() As String
    Dim i As Long, lvD As Level, s As String
    On Error Resume Next
    Set el = pEl.Item(j)
    If pRac(j) Then
        Set el.Level = oLuu: el.Rewrite
        If Err.Number = 0 Then nLuu = nLuu + 1
        Err.Clear
        Exit Sub
    End If
    If pNP(j) = 0 Then Exit Sub
    v = Split(pVai(j), "|"): tk = Split(pTok(j), "|"): vt = Split(pPos(j), "|")
    s = Trim$(pS(j))
    If pNP(j) = 1 And s = tk(0) And el.Type = msdElementTypeText Then
        Set lvD = PN_LopVai(v(0), oSo, oLD, oDT)
        If lvD Is Nothing Then Exit Sub
        If el.Level.Number <> lvD.Number Then
            Set el.Level = lvD: el.Rewrite
            If Err.Number = 0 Then nDoi = nDoi + 1
        End If
        Err.Clear
        Exit Sub
    End If
    ' tao chu tach
    Set c = PN_ChuDon(el)
    If c Is Nothing Then Exit Sub
    Set te = c
    Dim rot As Matrix3d, dx As Double, dy As Double, L As Double, h As Double, rw As Double, rh As Double
    Dim cx As Double, cy As Double, ca As Double, sa As Double, f As Double, nt As TextElement, ts As Object
    Dim moi As New Collection, nLen As Long
    rot = te.Rotation
    dx = rot.RowX.x: dy = rot.RowY.x
    If Err.Number <> 0 Then Err.Clear: dx = 1#: dy = 0#
    L = Sqr(dx * dx + dy * dy): If L <= 0 Then dx = 1#: dy = 0#: L = 1#
    dx = dx / L: dy = dy / L
    h = te.TextStyle.Height
    rw = el.Range.High.x - el.Range.Low.x: rh = el.Range.High.y - el.Range.Low.y
    cx = (el.Range.High.x + el.Range.Low.x) / 2#: cy = (el.Range.High.y + el.Range.Low.y) / 2#
    ca = Abs(dx): sa = Abs(dy)
    If ca >= sa Then L = (rw - h * sa) / ca Else L = (rh - h * ca) / sa
    nLen = Len(te.Text): If nLen < 1 Then nLen = 1
    If L <= 0 Then L = nLen * h * 0.6
    For i = 0 To UBound(v)
        Set lvD = PN_LopVai(v(i), oSo, oLD, oDT)
        f = (CLng(vt(i)) - 1 + Len(tk(i)) / 2#) / nLen
        Set nt = Nothing
        Set nt = CreateTextElement1(c, tk(i), Point3dFromXYZ(cx + dx * (f - 0.5) * L, cy + dy * (f - 0.5) * L, 0#), rot)
        If nt Is Nothing Then Err.Clear: Exit Sub
        Set ts = nt.TextStyle
        ts.Justification = msdTextJustificationCenterCenter
        Set nt.TextStyle = ts
        Err.Clear
        nt.color = c.color
        If Not lvD Is Nothing Then Set nt.Level = lvD
        moi.Add nt
    Next i
    Err.Clear
    For i = 1 To moi.Count
        ActiveModelReference.AddElement moi.Item(i)
    Next i
    If Err.Number <> 0 Then Err.Clear: Exit Sub
    nMoi = nMoi + moi.Count
    Set el.Level = oLuu: el.Rewrite
    If Err.Number = 0 Then nLuu = nLuu + 1
    Err.Clear
End Sub

Private Function PN_LopVai(ByVal r As String, ByVal oSo As Level, ByVal oLD As Level, ByVal oDT As Level) As Level
    Select Case r
        Case "S", "B": Set PN_LopVai = oSo
        Case "L": Set PN_LopVai = oLD
        Case "D": Set PN_LopVai = oDT
    End Select
End Function

' Co chu thuong a-z hoac ky tu ngoai ASCII (ghi chu, ten duong, ma TCVN3...)
Private Function PN_CoChuThuong(ByVal s As String) As Boolean
    Dim i As Long, c As Long
    For i = 1 To Len(s)
        c = AscW(Mid$(s, i, 1)) And &HFFFF&
        If (c >= 97 And c <= 122) Or c > 127 Then PN_CoChuThuong = True: Exit Function
    Next i
End Function

Attribute VB_Name = "modSeedHS"
'============================================================
' modSeedHS - Chu ky he toa do cua ban ve dang mo (cho file seed luu ho so)
'   Moi he toa do (don vi UOR + goc toa do Global Origin) -> 1 file seed:
'   C:\DiaChinhVL\Mau\seed_hoso_<chu ky>.dgn. Cung he -> dung lai, nhanh.
'   Tach module rieng: neu object model khac phien ban thi chi anh huong
'   nut "Luu file ho so", khong anh huong trich luc.
'============================================================
Option Explicit

Public Function DC_ChuKySeed() As String
    Dim o As Object, u As Double, s As String, go As Point3d
    On Error Resume Next
    Set o = ActiveModelReference
    u = o.UORsPerMasterUnit
    s = "u" & SoTen(u)
    Err.Clear
    go = ActiveModelReference.GlobalOrigin
    If Err.Number = 0 Then s = s & "_x" & SoTen(go.x) & "_y" & SoTen(go.y)
    DC_ChuKySeed = s
End Function

Private Function SoTen(ByVal v As Double) As String
    Dim t As String
    t = Format$(Round(v, 3), "0.###")
    If Right$(t, 1) = "." Or Right$(t, 1) = "," Then t = Left$(t, Len(t) - 1)
    t = Replace(Replace(Replace(t, ".", "p"), ",", "p"), "-", "m")
    SoTen = t
End Function

Attribute VB_Name = "modTachHop"
'============================================================
' modTachHop - Ban ve TACH THUA / HOP THUA (Mau so 22/DK, TT26)
'   Tach : nguoi dung VE DUONG CAT truoc (level cat, mac dinh 18, hoac
'          chon san cac duong do) -> chia thua goc thanh cac thua con.
'   Hop  : chon 2+ thua lien ke -> ghep thanh 1 thua (bo canh chung).
'   Chi XUAT HO SO (khong sua ban do / CSDL).
'   So dinh: thua chinh (thua goc khi tach, thua moi khi hop) 1..n,
'            dinh moi / dinh rieng phia ben kia danh 1', 2', ...
'   Mau .dgn (22tach.dgn / 22hop.dgn): o so do truoc (level 25),
'   o so do sau (level 24), bang Doan/Chieu dai (chu "tt"/"cd").
'============================================================
Option Explicit

' 0 = tat (trich luc) ; 1 = tach ; 2 = hop. modMauDgn doc de thay chu mau.
Public gTHCheDo As Long

Private mGoc As Collection       ' thua TRUOC (tach: 1 thua goc ; hop: cac thua)
Private mSau As Collection       ' thua SAU  (tach: cac thua con ; hop: 1 thua)
Private mSoT As Object           ' so do TRUOC: "x|y" -> "1", "2"...
Private mSoS As Object           ' so do SAU  : "x|y" -> "1'", "2'"...
Private mDoanS As Collection     ' bang Doan (SAU): Array(so1, so2, chieu dai)
Private mTo As String, mDiaChi As String
' vi tri (y) cac dong "3.4.k Thua ..." va "- Tu diem ..." trong file mau
Private mHdK() As Long, mHdY() As Double, mNHd As Long
Private mTuY() As Double, mNTu As Long
' SUA 21/10: mau TT26 moi - dong "a) Thua so:" va muc d) "- Thua x:" / "+ Tu diem"
Private mAY() As Double, mNA As Long
Private mH2Y() As Double, mNH2 As Long
Private mY2 As Double, mCoY2 As Boolean     ' y dong "2. Thua dat thu hai"

' SUA 22/10: HOP thua - giu nguyen dinh (khong bo dinh thang hang) + canh chung ve net dut
Private mGiuDinh As Boolean
Private mChung As Collection
Private Const TOL_NUT As Double = 0.005      ' gop dinh gan nhau (m)

'============================================================
' LENH CHINH
'   cheDo 1 = tach (goc: 1 thua), 2 = hop (goc: >= 2 thua)
'============================================================
Public Sub DC_ChayTachHop(ByVal cheDo As Long, ByVal goc As Collection, _
                          ByVal mauPath As String, ByVal iniPath As String, _
                          ByVal toBanDo As String, ByVal tenXa As String, _
                          ByVal tenHuyen As String, ByVal tenTinh As String, _
                          ByVal tyLe As Double, ByVal lvCat As String)
    Dim tieuDe As String, Loi As String, i As Long, v As clsVung
    If cheDo = 2 Then tieuDe = "H" & ChrW(7907) & "p th" & ChrW(7917) & "a" Else tieuDe = "T" & ChrW(225) & "ch th" & ChrW(7917) & "a"
    If goc Is Nothing Then Exit Sub
    ' SUA 16/10/2026: lan truoc da tu tat lop -> bat lai truoc khi xuat
    If DC_DaTatLop() Then DC_BatLopBanDo
    If cheDo = 2 And goc.Count < 2 Then DC_ThongBao "Ch" & ChrW(7885) & "n " & ChrW(237) & "t nh" & ChrW(7845) & "t 2 th" & ChrW(7917) & "a " & ChrW(273) & ChrW(7875) & " h" & ChrW(7907) & "p.", tieuDe, vbExclamation: Exit Sub

    For i = 1 To goc.Count
        Set v = goc.Item(i)
        If Not v.HasRing Then DC_ThongBao "Th" & ChrW(7917) & "a " & v.soThua & " kh" & ChrW(244) & "ng c" & ChrW(243) & " h" & ChrW(236) & "nh h" & ChrW(7885) & "c.", tieuDe, vbExclamation: Exit Sub
        If Len(Trim$(v.soThua)) = 0 Then v.soThua = "0"
        If Len(Trim$(v.loaiDat)) = 0 Then v.loaiDat = "0"
        If v.dt <= 0 Then v.dt = TH_DienTich(v)
    Next i

    ' 1) Hinh hoc
    ' truoc = cac thua ve o so do TRUOC (va thong tin muc II thua goc)
    Dim sau As Collection, vChinh As clsVung, truoc As Collection
    Set truoc = goc
    If cheDo = 1 And goc.Count = 1 Then
        ' Tach theo DUONG CAT (level cat / phan tu dang chon)
        Set vChinh = goc.Item(1)
        Set sau = TH_CatThua(vChinh, lvCat, Loi)
        If sau Is Nothing Then DC_ThongBao Loi, tieuDe, vbExclamation: Exit Sub
    ElseIf cheDo = 1 Then
        ' SUA 11/10/2026: tach theo RANH DA CO - cac thua chon (vd 17 + 78) la
        ' cac thua con; thua goc = ghep cac thua do lai.
        Set vChinh = TH_HopThua(goc, Loi)
        If vChinh Is Nothing Then DC_ThongBao Loi, tieuDe, vbExclamation: Exit Sub
        Dim soGoc As String
        soGoc = InputBox("So thua GOC (truoc khi tach):", "Tach thua", Trim$(goc.Item(1).soThua))
        If Len(Trim$(soGoc)) = 0 Then Exit Sub
        vChinh.soThua = Trim$(soGoc)
        vChinh.dt = TH_DienTich(vChinh)
        ' SUA 22/10: thua con dat ten <goc>-1, -2 ... theo THU TU CHON
        For i = 1 To goc.Count
            goc.Item(i).soThua = vChinh.soThua & "-" & i
        Next i
        Set sau = goc
        Set truoc = New Collection
        truoc.Add vChinh
    Else
        mGiuDinh = True     ' SUA 22/10: hop -> giu nguyen cac dinh, so dinh nhu so do truoc
        Set vChinh = TH_HopThua(goc, Loi)
        mGiuDinh = False
        If vChinh Is Nothing Then DC_ThongBao Loi, tieuDe, vbExclamation: Exit Sub
        Set sau = New Collection
        sau.Add vChinh
    End If

    ' 2) So hieu dinh: moi vong bat dau tren-trai, chieu kim dong ho
    ChuanHoaVong vChinh
    For i = 1 To truoc.Count
        If Not truoc.Item(i) Is vChinh Then ChuanHoaVong truoc.Item(i)
    Next i
    For i = 1 To sau.Count
        If Not sau.Item(i) Is vChinh Then ChuanHoaVong sau.Item(i)
    Next i
    Set mGoc = truoc: Set mSau = sau
    DanhSo vChinh, truoc, sau

    ' 3) Thong tin chung
    mTo = Trim$(toBanDo)
    If Len(mTo) = 0 Then mTo = Trim$(truoc.Item(1).SoTo)
    If Len(mTo) = 0 Then mTo = DC_ToTheoTenFile()    ' SUA 22/10: so trong ten file (DC9 -> 9)
    If Len(mTo) = 0 Then mTo = "0"
    mDiaChi = DiaChiThua(tenXa, tenHuyen, tenTinh)

    ' 4) Mau + ty le
    mauPath = DC_ChuanBiMau(mauPath, iniPath)
    If Not DC_DatFontViet() Then
        DC_ThongBao "Kh" & ChrW(244) & "ng " & ChrW(273) & ChrW(7863) & "t " & ChrW(273) & ChrW(432) & ChrW(7907) & "c font ch" & ChrW(7919) & " ti" & ChrW(7871) & "ng Vi" & ChrW(7879) & "t, ch" & ChrW(7919) & " c" & ChrW(243) & " th" & ChrW(7875) & " kh" & ChrW(244) & "ng hi" & ChrW(7879) & "n.", tieuDe, vbExclamation
    End If
    Dim tuDong As Boolean
    If tyLe <= 0 Then
        ' SUA 11/10/2026: tinh theo CA 2 o so do (truoc 25 / sau 24) -> so do sau
        ' ve dung ty le that (kp = 1), trung khit ranh thua tren ban do.
        Dim bx1 As Double, by1 As Double, bx2 As Double, by2 As Double, rgC() As Double
        rgC = vChinh.ring
        BaoRing rgC, bx1, by1, bx2, by2
        tyLe = DC_TyLeTachHop(mauPath, bx2 - bx1, by2 - by1): tuDong = True
    End If

    ' 5) Ve
    gTHCheDo = cheDo
    On Error GoTo LoiVe
    gTyLeTuDong = tuDong
    ChenKhungTachHop cheDo, truoc, sau, vChinh, mauPath, mTo, tenXa, tenHuyen, tenTinh, tyLe
    DC_TraMauDien     ' SUA 22/10: tra mau dang dung
    On Error GoTo 0
    gTHCheDo = 0

    ' 6) Pham vi (zoom + Luu file ho so)
    Dim x1 As Double, y1 As Double, x2 As Double, y2 As Double
    If DC_PhamViKhung(mauPath, tyLe, gTLCx, gTLCy, x1, y1, x2, y2) Then
        gTLx1 = x1: gTLy1 = y1: gTLx2 = x2: gTLy2 = y2
        DC_ZoomVung x1, y1, x2, y2
    End If
    ' SUA 16/10/2026: xuat xong TU TAT lop ban do, chi de Level ho so + Level so do
    '   (giong trich luc; DiaChinhVL.ini -> TL_TUTATLOP=0 de tat)
    If DC_DocCauHinh("TL_TUTATLOP", "1") = "1" And DC_DocCauHinh("LV_HS_ON", "1") = "1" _
       And DC_DocCauHinh("LV_SD_ON", "1") = "1" Then
        If Len(Trim$(DC_DocCauHinh("LV_HS", ""))) > 0 And Len(Trim$(DC_DocCauHinh("LV_SD", ""))) > 0 Then
            DC_TatLopBanDo DC_DocCauHinh("LV_HS", ""), DC_DocCauHinh("LV_SD", "")
        End If
    End If
    If cheDo = 1 Then
        gTLTen = "TachThua_To" & mTo & "_Thua" & vChinh.soThua
    Else
        gTLTen = "HopThua_To" & mTo & "_Thua" & Replace(vChinh.soThua, "+", "_")
    End If

    ' 7) Bao ket qua
    Dim s As String, tong As Double
    For i = 1 To sau.Count
        Set v = sau.Item(i)
        s = s & "  - Th" & ChrW(7917) & "a " & v.soThua & ": " & SoDt(v.dt) & " m" & ChrW(178) & vbCrLf
        tong = tong + v.dt
    Next i
    If cheDo = 1 Then
        s = ChrW(272) & ChrW(227) & " t" & ChrW(225) & "ch th" & ChrW(7917) & "a " & vChinh.soThua & " (" & SoDt(vChinh.dt) & " m" & ChrW(178) & ") th" & ChrW(224) & "nh " & sau.Count & " th" & ChrW(7917) & "a:" & vbCrLf & s & _
            "  T" & ChrW(7893) & "ng: " & SoDt(tong) & " m" & ChrW(178)
    Else
        s = ChrW(272) & ChrW(227) & " h" & ChrW(7907) & "p " & goc.Count & " th" & ChrW(7917) & "a th" & ChrW(224) & "nh th" & ChrW(7917) & "a " & vChinh.soThua & ":" & vbCrLf & s
    End If
    s = s & vbCrLf & "T" & ChrW(7927) & " l" & ChrW(7879) & " 1:" & CStr(tyLe) & IIf(tuDong, " (t" & ChrW(7921) & " " & ChrW(273) & ChrW(7897) & "ng)", "")
    DC_ThongBao s, tieuDe
    Exit Sub
LoiVe:
    gTHCheDo = 0
    DC_TraMauDien
    DC_ThongBao "L" & ChrW(7895) & "i khi v" & ChrW(7869) & " b" & ChrW(7843) & "n v" & ChrW(7869) & ": " & Err.Description, tieuDe, vbExclamation
End Sub

'============================================================
' TACH: chia thua v bang cac duong cat
'============================================================
Public Function TH_CatThua(ByVal v As clsVung, ByVal lvCat As String, ByRef Loi As String) As Collection
    Dim rg() As Double, x1 As Double, y1 As Double, x2 As Double, y2 As Double, m As Long, i As Long
    rg = v.ring: m = UBound(rg, 1)
    BaoRing rg, x1, y1, x2, y2

    ' 1) Duong cat: level cat + phan tu dang chon
    Dim cat As New Collection
    LayDuongCat lvCat, x1, y1, x2, y2, cat
    If cat.Count = 0 Then
        Loi = "Kh" & ChrW(244) & "ng th" & ChrW(7845) & "y " & ChrW(273) & ChrW(432) & ChrW(7901) & "ng c" & ChrW(7855) & "t n" & ChrW(224) & "o c" & ChrW(7855) & "t qua th" & ChrW(7917) & "a " & v.soThua & "." & vbCrLf & _
              "H" & ChrW(227) & "y v" & ChrW(7869) & " " & ChrW(273) & ChrW(432) & ChrW(7901) & "ng c" & ChrW(7855) & "t (line/linestring) tr" & ChrW(234) & "n level " & lvCat & _
              " c" & ChrW(7855) & "t ngang th" & ChrW(7917) & "a, ho" & ChrW(7863) & "c ch" & ChrW(7885) & "n s" & ChrW(7861) & "n c" & ChrW(225) & "c " & ChrW(273) & ChrW(432) & ChrW(7901) & "ng c" & ChrW(7855) & "t r" & ChrW(7891) & "i l" & ChrW(224) & "m l" & ChrW(7841) & "i."
        Exit Function
    End If

    ' 2) Gom doan: ranh thua (ngoai + dao) + duong cat -> cat nhau tai giao diem
    Dim segs As New Collection, k As Long, dr() As Double
    For i = 0 To m - 1
        segs.Add NewSeg(rg(i, 0), rg(i, 1), rg(i + 1, 0), rg(i + 1, 1))
    Next i
    For k = 1 To v.dao.Count
        dr = v.dao.Item(k)
        For i = 0 To UBound(dr, 1) - 1
            segs.Add NewSeg(dr(i, 0), dr(i, 1), dr(i + 1, 0), dr(i + 1, 1))
        Next i
    Next k
    For i = 1 To cat.Count
        segs.Add cat.Item(i)
    Next i
    Dim segN As Collection
    Set segN = TH_NoiDoan(segs, TOL_NUT)

    ' 3) Ghep vung -> cac mat nam trong thua goc
    Dim vungs As Collection, tia As Long, w As clsVung, con As New Collection
    Set vungs = GhepVung(segN, TOL_NUT / 5#, tia)
    For i = 1 To vungs.Count
        Set w = vungs.Item(i)
        If w.dt > 0.01 Then
            If TrongThua(v, w) Then con.Add w
        End If
    Next i
    If con.Count < 2 Then
        Loi = ChrW(272) & ChrW(432) & ChrW(7901) & "ng c" & ChrW(7855) & "t ch" & ChrW(432) & "a chia " & ChrW(273) & ChrW(432) & ChrW(7907) & "c th" & ChrW(7917) & "a " & v.soThua & " (ch" & ChrW(7881) & " " & ChrW(273) & ChrW(432) & ChrW(7907) & "c " & con.Count & " ph" & ChrW(7847) & "n)." & vbCrLf & _
              ChrW(272) & ChrW(432) & ChrW(7901) & "ng c" & ChrW(7855) & "t ph" & ChrW(7843) & "i c" & ChrW(7855) & "t h" & ChrW(7859) & "n qua ranh th" & ChrW(7917) & "a (v" & ChrW(7869) & " d" & ChrW(432) & " ra ngo" & ChrW(224) & "i ranh m" & ChrW(7897) & "t ch" & ChrW(250) & "t)."
        Exit Function
    End If

    ' 4) Sap thu tu: tren xuong, trai sang phai ; dat so tam "843-1"...
    Dim kq As Collection
    Set kq = SapDocDoc(con, (y2 - y1) * 0.15)
    For i = 1 To kq.Count
        Set w = kq.Item(i)
        w.soThua = Trim$(v.soThua) & "-" & i
        w.SoTo = v.SoTo: w.loaiDat = v.loaiDat
        w.TenChu = v.TenChu: w.DiaChi = v.DiaChi: w.tenXa = v.tenXa
    Next i
    Set TH_CatThua = kq
End Function

' Mat w nam trong thua goc v (diem trong cua w o trong ranh ngoai, ngoai cac dao)
Private Function TrongThua(ByVal v As clsVung, ByVal w As clsVung) As Boolean
    Dim rg() As Double, k As Long, dr() As Double, px As Double, py As Double
    DiemTrongMat w, px, py
    rg = v.ring
    If Not DiemTrongPolygon(rg, px, py) Then Exit Function
    For k = 1 To v.dao.Count
        dr = v.dao.Item(k)
        If DiemTrongPolygon(dr, px, py) Then Exit Function
    Next k
    TrongThua = True
End Function

' Diem chac chan nam trong mat w: giua canh dai nhat, lech vao trong (mat CCW -> ben trai)
Private Sub DiemTrongMat(ByVal w As clsVung, ByRef px As Double, ByRef py As Double)
    Dim rg() As Double, i As Long, m As Long, L As Double, best As Double, ib As Long, e As Double
    rg = w.ring: m = UBound(rg, 1)
    For i = 0 To m - 1
        L = Sqr((rg(i + 1, 0) - rg(i, 0)) ^ 2 + (rg(i + 1, 1) - rg(i, 1)) ^ 2)
        If L > best Then best = L: ib = i
    Next i
    px = w.cx: py = w.cy
    If best <= 0 Then Exit Sub
    e = best * 0.001: If e > 0.01 Then e = 0.01
    px = (rg(ib, 0) + rg(ib + 1, 0)) / 2# - (rg(ib + 1, 1) - rg(ib, 1)) / best * e
    py = (rg(ib, 1) + rg(ib + 1, 1)) / 2# + (rg(ib + 1, 0) - rg(ib, 0)) / best * e
End Sub

' Lay doan thang cua duong cat: phan tu tren level cat + phan tu dang chon,
' chi lay phan tu co khung bao cham khung thua.
Private Sub LayDuongCat(ByVal lvCat As String, ByVal x1 As Double, ByVal y1 As Double, _
                        ByVal x2 As Double, ByVal y2 As Double, ByVal cat As Collection)
    Dim dS() As Long, c As Long, i As Long, lvOk As Object
    Set lvOk = CreateObject("Scripting.Dictionary")
    c = DC_DsSoLevel(lvCat, dS)
    For i = 0 To c - 1
        lvOk(CStr(dS(i))) = True
    Next i

    Dim esc As New ElementScanCriteria, ee As ElementEnumerator, el As Element
    esc.ExcludeAllTypes
    esc.IncludeType msdElementTypeLine
    esc.IncludeType msdElementTypeLineString
    esc.IncludeType msdElementTypeComplexString
    If c > 0 Then
        Set ee = ActiveModelReference.Scan(esc)
        Do While ee.MoveNext
            Set el = ee.Current
            If lvOk.Exists(CStr(DC_LevelSo(el))) Then ThemDoanEl el, x1, y1, x2, y2, cat
        Loop
    End If
    ' phan tu dang chon (moi level)
    On Error Resume Next
    Set ee = Nothing
    Set ee = ActiveModelReference.GetSelectedElements
    On Error GoTo 0
    If Not ee Is Nothing Then
        Do While ee.MoveNext
            Set el = ee.Current
            If Not lvOk.Exists(CStr(DC_LevelSo(el))) Then ThemDoanEl el, x1, y1, x2, y2, cat
        Loop
    End If
End Sub

Private Sub ThemDoanEl(ByVal el As Element, ByVal x1 As Double, ByVal y1 As Double, _
                       ByVal x2 As Double, ByVal y2 As Double, ByVal cat As Collection)
    Dim rgE As Range3d, pts() As Point3d, i As Long, subs As ElementEnumerator, d As Double
    On Error Resume Next
    rgE = el.Range
    If Err.Number <> 0 Then Exit Sub
    d = ((x2 - x1) + (y2 - y1)) * 0.02
    If rgE.High.x < x1 - d Or rgE.Low.x > x2 + d Or rgE.High.y < y1 - d Or rgE.Low.y > y2 + d Then Exit Sub
    If el.Type = msdElementTypeComplexString Then
        Set subs = el.AsComplexElement.GetSubElements
        Do While subs.MoveNext
            ThemDoanEl subs.Current, x1, y1, x2, y2, cat
        Loop
        Exit Sub
    End If
    If Not el.IsVertexList Then Exit Sub
    Err.Clear
    pts = el.AsVertexList.GetVertices
    If Err.Number <> 0 Then Exit Sub
    On Error GoTo 0
    For i = LBound(pts) To UBound(pts) - 1
        If Abs(pts(i + 1).x - pts(i).x) + Abs(pts(i + 1).y - pts(i).y) > TOL_NUT Then
            cat.Add NewSeg(pts(i).x, pts(i).y, pts(i + 1).x, pts(i + 1).y)
        End If
    Next i
End Sub

'============================================================
' NOI DOAN: cat moi doan tai giao diem voi doan khac (ke ca diem cham),
' gop cac dinh gan nhau (< tol) ve 1 toa do -> tra ve tap doan moi.
'============================================================
Public Function TH_NoiDoan(ByVal segs As Collection, ByVal tol As Double) As Collection
    Dim n As Long, i As Long, j As Long, s() As Double
    n = segs.Count
    Dim ax() As Double, ay() As Double, bx() As Double, by() As Double, dl() As Double
    ReDim ax(1 To n): ReDim ay(1 To n): ReDim bx(1 To n): ReDim by(1 To n): ReDim dl(1 To n)
    For i = 1 To n
        s = segs.Item(i)
        ax(i) = s(0): ay(i) = s(1): bx(i) = s(2): by(i) = s(3)
        dl(i) = Sqr((bx(i) - ax(i)) ^ 2 + (by(i) - ay(i)) ^ 2)
    Next i

    ' moi doan: danh sach (t, x, y) diem cat
    Dim tL() As Collection
    ReDim tL(1 To n)
    For i = 1 To n
        Set tL(i) = New Collection
        tL(i).Add Array(0#, ax(i), ay(i))
        tL(i).Add Array(1#, bx(i), by(i))
    Next i

    Dim d1x As Double, d1y As Double, d2x As Double, d2y As Double, den As Double
    Dim wx As Double, wy As Double, t As Double, u As Double, eT As Double, eU As Double
    Dim px As Double, py As Double
    For i = 1 To n - 1
        If dl(i) <= tol Then GoTo TiepI
        d1x = bx(i) - ax(i): d1y = by(i) - ay(i)
        For j = i + 1 To n
            If dl(j) <= tol Then GoTo TiepJ
            ' loai nhanh theo khung bao
            If Max2(ax(i), bx(i)) + tol < Min2(ax(j), bx(j)) Then GoTo TiepJ
            If Max2(ax(j), bx(j)) + tol < Min2(ax(i), bx(i)) Then GoTo TiepJ
            If Max2(ay(i), by(i)) + tol < Min2(ay(j), by(j)) Then GoTo TiepJ
            If Max2(ay(j), by(j)) + tol < Min2(ay(i), by(i)) Then GoTo TiepJ
            d2x = bx(j) - ax(j): d2y = by(j) - ay(j)
            den = d1x * d2y - d1y * d2x
            eT = tol / dl(i): eU = tol / dl(j)
            If Abs(den) <= 0.000000001 * dl(i) * dl(j) Then
                ' song song: dau mut cua doan nay nam tren doan kia
                ThemChieu tL(i), ax(i), ay(i), d1x, d1y, dl(i), ax(j), ay(j), tol
                ThemChieu tL(i), ax(i), ay(i), d1x, d1y, dl(i), bx(j), by(j), tol
                ThemChieu tL(j), ax(j), ay(j), d2x, d2y, dl(j), ax(i), ay(i), tol
                ThemChieu tL(j), ax(j), ay(j), d2x, d2y, dl(j), bx(i), by(i), tol
            Else
                wx = ax(j) - ax(i): wy = ay(j) - ay(i)
                t = (wx * d2y - wy * d2x) / den
                u = (wx * d1y - wy * d1x) / den
                If t >= -eT And t <= 1# + eT And u >= -eU And u <= 1# + eU Then
                    ' uu tien dau mut co san (tranh tao diem lech)
                    If t <= eT Then
                        px = ax(i): py = ay(i): t = 0#
                    ElseIf t >= 1# - eT Then
                        px = bx(i): py = by(i): t = 1#
                    ElseIf u <= eU Then
                        px = ax(j): py = ay(j)
                    ElseIf u >= 1# - eU Then
                        px = bx(j): py = by(j)
                    Else
                        px = ax(i) + t * d1x: py = ay(i) + t * d1y
                    End If
                    If u < 0# Then u = 0#
                    If u > 1# Then u = 1#
                    If t < 0# Then t = 0#
                    If t > 1# Then t = 1#
                    If u <= eU Then u = 0# Else If u >= 1# - eU Then u = 1#
                    tL(i).Add Array(t, px, py)
                    tL(j).Add Array(u, px, py)
                End If
            End If
TiepJ:
        Next j
TiepI:
    Next i

    ' gop dinh gan nhau -> toa do chuan
    Dim nutX As New Collection, nutY As New Collection
    Dim kq As New Collection, a() As Variant, na As Long, q As Long, r As Long, tmp As Variant
    Dim p1x As Double, p1y As Double, p2x As Double, p2y As Double
    For i = 1 To n
        If dl(i) <= tol Then GoTo TiepK
        na = tL(i).Count
        ReDim a(1 To na)
        For q = 1 To na
            a(q) = tL(i).Item(q)
        Next q
        For q = 2 To na                          ' sap theo t
            tmp = a(q): r = q - 1
            Do While r >= 1
                If a(r)(0) > tmp(0) Then a(r + 1) = a(r): r = r - 1 Else Exit Do
            Loop
            a(r + 1) = tmp
        Next q
        ChuanNut a(1)(1), a(1)(2), tol, nutX, nutY, p1x, p1y
        For q = 2 To na
            ChuanNut a(q)(1), a(q)(2), tol, nutX, nutY, p2x, p2y
            If Abs(p2x - p1x) + Abs(p2y - p1y) > tol * 0.01 Then
                kq.Add NewSeg(p1x, p1y, p2x, p2y)
                p1x = p2x: p1y = p2y
            End If
        Next q
TiepK:
    Next i
    Set TH_NoiDoan = kq
End Function

' Diem (qx,qy) nam tren doan (o + s*d) -> them vao danh sach cat
Private Sub ThemChieu(ByVal tL As Collection, ByVal ox As Double, ByVal oy As Double, _
                      ByVal dx As Double, ByVal dy As Double, ByVal dd As Double, _
                      ByVal qx As Double, ByVal qy As Double, ByVal tol As Double)
    Dim t As Double, kc As Double
    If dd <= 0 Then Exit Sub
    t = ((qx - ox) * dx + (qy - oy) * dy) / (dd * dd)
    kc = Abs((qx - ox) * dy - (qy - oy) * dx) / dd
    If kc <= tol And t > tol / dd And t < 1# - tol / dd Then tL.Add Array(t, qx, qy)
End Sub

Private Sub ChuanNut(ByVal x As Double, ByVal y As Double, ByVal tol As Double, _
                     ByVal nutX As Collection, ByVal nutY As Collection, _
                     ByRef rx As Double, ByRef ry As Double)
    Dim i As Long
    For i = 1 To nutX.Count
        If Abs(nutX.Item(i) - x) <= tol And Abs(nutY.Item(i) - y) <= tol Then
            rx = nutX.Item(i): ry = nutY.Item(i): Exit Sub
        End If
    Next i
    nutX.Add x: nutY.Add y
    rx = x: ry = y
End Sub

Private Function Max2(ByVal a As Double, ByVal b As Double) As Double
    If a > b Then Max2 = a Else Max2 = b
End Function
Private Function Min2(ByVal a As Double, ByVal b As Double) As Double
    If a < b Then Min2 = a Else Min2 = b
End Function

'============================================================
' HOP: ghep cac thua lien ke (bo canh chung) -> 1 thua
'============================================================
Public Function TH_HopThua(ByVal dS As Collection, ByRef Loi As String) As clsVung
    Dim dem As Object, doan As Object, i As Long, k As Long, v As clsVung
    Dim rg() As Double, key As String, ka As String, kB As String
    Set dem = CreateObject("Scripting.Dictionary")
    Set doan = CreateObject("Scripting.Dictionary")
    For i = 1 To dS.Count
        Set v = dS.Item(i)
        For k = 0 To v.dao.Count
            If k = 0 Then rg = v.ring Else rg = v.dao.Item(k)
            ThemCanhHop rg, dem, doan
        Next k
    Next i

    Dim segs As New Collection, kk As Variant
    Set mChung = New Collection
    For Each kk In dem.Keys
        If dem(kk) = 1 Then segs.Add doan(kk)
        If dem(kk) >= 2 Then mChung.Add doan(kk)     ' SUA 22/10: canh chung giua cac thua
    Next kk
    If segs.Count < 3 Then Loi = "Kh" & ChrW(244) & "ng gh" & ChrW(233) & "p " & ChrW(273) & ChrW(432) & ChrW(7907) & "c c" & ChrW(225) & "c th" & ChrW(7917) & "a " & ChrW(273) & ChrW(227) & " ch" & ChrW(7885) & "n.": Exit Function

    Dim vungs As Collection, tia As Long, w As clsVung, best As clsVung, aMax As Double, a As Double
    Set vungs = GhepVung(segs, TOL_NUT / 5#, tia)
    For i = 1 To vungs.Count
        Set w = vungs.Item(i)
        rg = w.ring
        a = Abs(DtRing(rg))
        If a > aMax Then aMax = a: Set best = w
    Next i
    If best Is Nothing Then Loi = "Kh" & ChrW(244) & "ng gh" & ChrW(233) & "p " & ChrW(273) & ChrW(432) & ChrW(7907) & "c c" & ChrW(225) & "c th" & ChrW(7917) & "a " & ChrW(273) & ChrW(227) & " ch" & ChrW(7885) & "n.": Exit Function

    ' Bo cac dinh thang hang tren ranh ngoai do canh chung de lai (vd diem dau
    ' duong cat cu) -> thua ghep chi con dinh goc that.
    BoDinhThangHang best, dem

    ' moi thua phai nam trong thua moi (lien ke nhau)
    Dim sTen As String, sLoai As String, tong As Double, rgB() As Double
    rgB = best.ring
    For i = 1 To dS.Count
        Set v = dS.Item(i)
        If Not DiemTrongPolygon(rgB, v.cx, v.cy) Then
            Loi = "Th" & ChrW(7917) & "a " & v.soThua & " kh" & ChrW(244) & "ng li" & ChrW(7873) & "n k" & ChrW(7873) & " v" & ChrW(7899) & "i c" & ChrW(225) & "c th" & ChrW(7917) & "a c" & ChrW(242) & "n l" & ChrW(7841) & "i (kh" & ChrW(244) & "ng chung c" & ChrW(7841) & "nh)." & vbCrLf & _
                  "Ch" & ChrW(7881) & " h" & ChrW(7907) & "p " & ChrW(273) & ChrW(432) & ChrW(7907) & "c c" & ChrW(225) & "c th" & ChrW(7917) & "a c" & ChrW(243) & " chung c" & ChrW(7841) & "nh."
            Exit Function
        End If
        If Len(sTen) > 0 Then sTen = sTen & "+"
        sTen = sTen & Trim$(v.soThua)
        If InStr(1, "+" & sLoai & "+", "+" & Trim$(v.loaiDat) & "+", vbTextCompare) = 0 Then
            If Len(sLoai) > 0 Then sLoai = sLoai & "+"
            sLoai = sLoai & Trim$(v.loaiDat)
        End If
        tong = tong + v.dt
    Next i
    Set v = dS.Item(1)
    best.soThua = sTen: best.loaiDat = sLoai: best.dt = tong
    best.SoTo = v.SoTo: best.TenChu = v.TenChu: best.DiaChi = v.DiaChi: best.tenXa = v.tenXa
    Set TH_HopThua = best
End Function

Private Sub BoDinhThangHang(ByVal w As clsVung, ByVal dem As Object)
    Dim chung As Object, kk As Variant, p As Long
    If mGiuDinh Then Exit Sub        ' SUA 22/10: hop thua giu nguyen dinh
    Set chung = CreateObject("Scripting.Dictionary")
    For Each kk In dem.Keys                      ' dau mut cac canh chung (dem = 2)
        If dem(kk) >= 2 Then
            p = InStr(kk, "#")
            chung(Left$(kk, p - 1)) = True: chung(Mid$(kk, p + 1)) = True
        End If
    Next kk
    Dim rg() As Double, m As Long, i As Long, n As Long, giu() As Boolean
    Dim ax As Double, ay As Double, bx As Double, by As Double, cx As Double, cy As Double, L As Double
    rg = w.ring: m = UBound(rg, 1)
    If m < 4 Then Exit Sub
    ReDim giu(0 To m - 1)
    For i = 0 To m - 1
        giu(i) = True
        If chung.Exists(KhoaDiem(rg(i, 0), rg(i, 1))) Then
            ax = rg((i + m - 1) Mod m, 0): ay = rg((i + m - 1) Mod m, 1)
            bx = rg((i + 1) Mod m, 0): by = rg((i + 1) Mod m, 1)
            cx = rg(i, 0): cy = rg(i, 1)
            L = Sqr((bx - ax) ^ 2 + (by - ay) ^ 2)
            If L > 0 Then
                If Abs((bx - ax) * (cy - ay) - (by - ay) * (cx - ax)) / L < 0.01 Then giu(i) = False
            End If
        End If
        If giu(i) Then n = n + 1
    Next i
    If n = m Or n < 3 Then Exit Sub
    Dim r2() As Double, j As Long
    ReDim r2(0 To n, 0 To 1)
    For i = 0 To m - 1
        If giu(i) Then r2(j, 0) = rg(i, 0): r2(j, 1) = rg(i, 1): j = j + 1
    Next i
    r2(n, 0) = r2(0, 0): r2(n, 1) = r2(0, 1)
    w.ring = r2
End Sub

Private Sub ThemCanhHop(rg() As Double, ByVal dem As Object, ByVal doan As Object)
    Dim i As Long, ka As String, kB As String, key As String
    For i = 0 To UBound(rg, 1) - 1
        ka = KhoaDiem(rg(i, 0), rg(i, 1)): kB = KhoaDiem(rg(i + 1, 0), rg(i + 1, 1))
        If ka <> kB Then
            If ka < kB Then key = ka & "#" & kB Else key = kB & "#" & ka
            If dem.Exists(key) Then
                dem(key) = dem(key) + 1
            Else
                dem.Add key, 1
                doan.Add key, NewSeg(rg(i, 0), rg(i, 1), rg(i + 1, 0), rg(i + 1, 1))
            End If
        End If
    Next i
End Sub

'============================================================
' SO HIEU DINH (theo mau TT26):
'   So do TRUOC: 1, 2, 3...   So do SAU: 1', 2', 3'... (TAT CA dinh co dau ')
'   Thu tu: di theo ranh ngoai cua thua chinh (vChinh) tu dinh dau, gap dinh
'   nao nam tren ranh thi danh tiep; roi den cac dinh ben trong (duong cat).
'   Bang Doan: cac canh ranh ngoai theo thu tu, roi cac canh ben trong.
'============================================================
Private Sub DanhSo(ByVal vChinh As clsVung, ByVal truoc As Collection, ByVal sau As Collection)
    Set mSoT = DanhSoTap(vChinh, truoc, "")
    Set mSoS = DanhSoTap(vChinh, sau, "'")
    Dim j As Long
    For j = 1 To sau.Count
        XoayVong sau.Item(j)
    Next j
    LapBangDoan vChinh, sau
End Sub

Private Function DanhSoTap(ByVal vChinh As clsVung, ByVal dS As Collection, ByVal dau As String) As Object
    Dim so As Object, toaX As Object, toaY As Object, n As Long
    Set so = CreateObject("Scripting.Dictionary")
    Set toaX = CreateObject("Scripting.Dictionary")
    Set toaY = CreateObject("Scripting.Dictionary")
    Dim j As Long, kv As Long, i As Long, rg() As Double, v As clsVung, key As String
    ' tap dinh cua cac thua
    For j = 1 To dS.Count
        Set v = dS.Item(j)
        For kv = 0 To v.dao.Count
            If kv = 0 Then rg = v.ring Else rg = v.dao.Item(kv)
            For i = 0 To UBound(rg, 1) - 1
                key = KhoaDiem(rg(i, 0), rg(i, 1))
                If Not toaX.Exists(key) Then toaX.Add key, rg(i, 0): toaY.Add key, rg(i, 1)
            Next i
        Next kv
    Next j
    ' 1) dinh tren ranh ngoai thua chinh, theo thu tu
    Dim ds2 As Collection, q As Long
    Set ds2 = DinhTrenRanh(vChinh, toaX, toaY)
    For q = 1 To ds2.Count
        key = ds2.Item(q)
        If Not so.Exists(key) Then n = n + 1: so.Add key, CStr(n) & dau
    Next q
    ' 2) dinh con lai (ben trong) theo thu tu xuat hien
    For j = 1 To dS.Count
        Set v = dS.Item(j)
        For kv = 0 To v.dao.Count
            If kv = 0 Then rg = v.ring Else rg = v.dao.Item(kv)
            For i = 0 To UBound(rg, 1) - 1
                key = KhoaDiem(rg(i, 0), rg(i, 1))
                If Not so.Exists(key) Then n = n + 1: so.Add key, CStr(n) & dau
            Next i
        Next kv
    Next j
    Set DanhSoTap = so
End Function

' Cac dinh (khoa) nam tren ranh ngoai vChinh, xep theo chieu di cua ranh
Private Function DinhTrenRanh(ByVal vChinh As clsVung, ByVal toaX As Object, ByVal toaY As Object) As Collection
    Dim kq As New Collection, rg() As Double, m As Long, i As Long, kk As Variant
    Dim ax As Double, ay As Double, dx As Double, dy As Double, L2 As Double
    Dim t As Double, kc As Double, px As Double, py As Double
    Dim tt() As Double, kt() As String, nt As Long, a As Long, b As Long, tmpT As Double, tmpK As String
    rg = vChinh.ring: m = UBound(rg, 1)
    ReDim tt(1 To toaX.Count + 1): ReDim kt(1 To toaX.Count + 1)
    For i = 0 To m - 1
        ax = rg(i, 0): ay = rg(i, 1): dx = rg(i + 1, 0) - ax: dy = rg(i + 1, 1) - ay
        L2 = dx * dx + dy * dy
        If L2 <= 0 Then GoTo TiepCanh
        nt = 0
        For Each kk In toaX.Keys
            px = toaX(kk): py = toaY(kk)
            t = ((px - ax) * dx + (py - ay) * dy) / L2
            If t >= -0.000001 And t < 1# - 0.000001 Then
                kc = Abs((px - ax) * dy - (py - ay) * dx) / Sqr(L2)
                If kc <= TOL_NUT Then nt = nt + 1: tt(nt) = t: kt(nt) = CStr(kk)
            End If
        Next kk
        For a = 2 To nt                      ' sap theo t
            tmpT = tt(a): tmpK = kt(a): b = a - 1
            Do While b >= 1
                If tt(b) > tmpT Then tt(b + 1) = tt(b): kt(b + 1) = kt(b): b = b - 1 Else Exit Do
            Loop
            tt(b + 1) = tmpT: kt(b + 1) = tmpK
        Next a
        For a = 1 To nt
            kq.Add kt(a)
        Next a
TiepCanh:
    Next i
    Set DinhTrenRanh = kq
End Function

' Bang Doan (so do SAU): canh ranh ngoai theo thu tu, roi canh ben trong
Private Sub LapBangDoan(ByVal vChinh As clsVung, ByVal sau As Collection)
    Dim canh As Object, daDung As Object, j As Long, kv As Long, i As Long, rg() As Double, v As clsVung
    Dim ka As String, kB As String, key As String
    Set canh = CreateObject("Scripting.Dictionary")      ' khoa canh -> Array(kA, kB, dai)
    Set daDung = CreateObject("Scripting.Dictionary")
    Set mDoanS = New Collection
    Dim thuTu As New Collection
    For j = 1 To sau.Count
        Set v = sau.Item(j)
        For kv = 0 To v.dao.Count
            If kv = 0 Then rg = v.ring Else rg = v.dao.Item(kv)
            For i = 0 To UBound(rg, 1) - 1
                ka = KhoaDiem(rg(i, 0), rg(i, 1)): kB = KhoaDiem(rg(i + 1, 0), rg(i + 1, 1))
                If ka < kB Then key = ka & "#" & kB Else key = kB & "#" & ka
                If Not canh.Exists(key) Then
                    canh.Add key, Array(ka, kB, Sqr((rg(i + 1, 0) - rg(i, 0)) ^ 2 + (rg(i + 1, 1) - rg(i, 1)) ^ 2))
                    thuTu.Add key
                End If
            Next i
        Next kv
    Next j
    ' 1) ranh ngoai: cac dinh SAU nam tren ranh, noi lien tiep (vong kin)
    Dim toaX As Object, toaY As Object, kk As Variant, dS As Collection, q As Long, a As String, b As String
    Set toaX = CreateObject("Scripting.Dictionary"): Set toaY = CreateObject("Scripting.Dictionary")
    For j = 1 To sau.Count
        Set v = sau.Item(j)
        For kv = 0 To v.dao.Count
            If kv = 0 Then rg = v.ring Else rg = v.dao.Item(kv)
            For i = 0 To UBound(rg, 1) - 1
                ka = KhoaDiem(rg(i, 0), rg(i, 1))
                If Not toaX.Exists(ka) Then toaX.Add ka, rg(i, 0): toaY.Add ka, rg(i, 1)
            Next i
        Next kv
    Next j
    Set dS = DinhTrenRanh(vChinh, toaX, toaY)
    For q = 1 To dS.Count
        a = dS.Item(q)
        If q < dS.Count Then b = dS.Item(q + 1) Else b = dS.Item(1)
        If a < b Then key = a & "#" & b Else key = b & "#" & a
        If canh.Exists(key) And Not daDung.Exists(key) Then
            daDung.Add key, True
            mDoanS.Add Array(mSoS(a), mSoS(b), canh(key)(2))
        End If
    Next q
    ' 2) canh con lai (duong cat, dao)
    Dim e As Variant
    For q = 1 To thuTu.Count
        key = thuTu.Item(q)
        If Not daDung.Exists(key) Then
            daDung.Add key, True
            e = canh(key)
            mDoanS.Add Array(mSoS(e(0)), mSoS(e(1)), e(2))
        End If
    Next q
End Sub

' Bang doan cho modKhungMau: so dong, tung dong (doan, chieu dai)
Public Function TH_SoDoan() As Long
    If mDoanS Is Nothing Then Exit Function
    TH_SoDoan = mDoanS.Count
End Function
Public Sub TH_Doan(ByVal i As Long, ByRef doan As String, ByRef dai As Double)
    Dim e As Variant
    e = mDoanS.Item(i)
    doan = e(0) & " - " & e(1): dai = e(2)
End Sub

' So hieu dinh tai (x,y): sau = True -> so do SAU (co dau '), False -> TRUOC
Public Function TH_SoDinh(ByVal x As Double, ByVal y As Double, Optional ByVal sau As Boolean = True) As String
    Dim key As String, d As Object
    If sau Then Set d = mSoS Else Set d = mSoT
    If d Is Nothing Then Exit Function
    key = KhoaDiem(x, y)
    If d.Exists(key) Then TH_SoDinh = d(key)
End Function

' Xoay vong ngoai thua SAU: dinh dau = dinh co so nho nhat
Private Sub XoayVong(ByVal v As clsVung)
    Dim rg() As Double, m As Long, i As Long, best As Long, bestSo As Long, key As String
    rg = v.ring: m = UBound(rg, 1)
    best = 0: bestSo = 2147483647
    For i = 0 To m - 1
        key = KhoaDiem(rg(i, 0), rg(i, 1))
        If mSoS.Exists(key) Then
            If CLng(val(mSoS(key))) < bestSo Then bestSo = CLng(val(mSoS(key))): best = i
        End If
    Next i
    If best = 0 Then Exit Sub
    Dim r2() As Double
    ReDim r2(0 To m, 0 To 1)
    For i = 0 To m - 1
        r2(i, 0) = rg((i + best) Mod m, 0): r2(i, 1) = rg((i + best) Mod m, 1)
    Next i
    r2(m, 0) = r2(0, 0): r2(m, 1) = r2(0, 1)
    v.ring = r2
End Sub

Private Function KhoaDiem(ByVal x As Double, ByVal y As Double) As String
    KhoaDiem = Format$(Round(x, 3), "0.000") & "|" & Format$(Round(y, 3), "0.000")
End Function

'============================================================
' THAY CHU MAU (goi tu modMauDgn.DC_ChepMauDgn khi gTHCheDo > 0)
'   s = chu mau (Unicode), y = toa do Y goc chu trong file mau
'   bo = True -> khong chep dong nay. Tra ve chu moi (= s neu giu nguyen).
'============================================================
Public Sub TH_BatDauViTri()
    mNHd = 0: mNTu = 0
    ReDim mHdK(1 To 32): ReDim mHdY(1 To 32): ReDim mTuY(1 To 64)
    ' SUA 21/10: mau TT26 moi
    ReDim mAY(1 To 16): ReDim mH2Y(1 To 32): mNA = 0: mNH2 = 0
    mCoY2 = False
End Sub

' Luot 1: ghi vi tri cac dong "3.4.k Thua" va "- Tu diem"
Public Sub TH_GhiViTri(ByVal s As String, ByVal y As Double)
    Dim k As Long
    s = Trim$(s)
    k = SoMuc34(s)
    If k > 0 Then
        If mNHd < UBound(mHdK) Then mNHd = mNHd + 1: mHdK(mNHd) = k: mHdY(mNHd) = y
    ElseIf Left$(s, 9) = "- T" & ChrW(7915) & " " & ChrW(273) & "i" & ChrW(7875) & "m" Then
        If mNTu < UBound(mTuY) Then mNTu = mNTu + 1: mTuY(mNTu) = y
    End If
    ' SUA 21/10: mau TT26 moi
    If batDau(s, "2. Th" & ChrW(7917) & "a " & ChrW(273) & ChrW(7845) & "t th" & ChrW(7913) & " hai") Then mY2 = y: mCoY2 = True
    If LaDongThuaSo(s) Then
        If mNA < UBound(mAY) Then mNA = mNA + 1: mAY(mNA) = y
    ElseIf LaTieuDeMoi(s) Then
        If mNH2 < UBound(mH2Y) Then mNH2 = mNH2 + 1: mH2Y(mNH2) = y
    ElseIf batDau(s, "+ T" & ChrW(7915) & " " & ChrW(273) & "i" & ChrW(7875) & "m") Then
        If mNTu < UBound(mTuY) Then mNTu = mNTu + 1: mTuY(mNTu) = y
    End If
End Sub

Public Function TH_ThayChu(ByVal s As String, ByVal y As Double, ByRef bo As Boolean) As String
    Dim t As String, k As Long, v As clsVung, cd As String
    bo = False
    TH_ThayChu = s
    If mSau Is Nothing Then Exit Function
    t = Trim$(s)
    ' SUA 22/10: tag rieng cho THUA GOC THU 2 (mau tach tung doan):
    '   soHieuThua2, toBanDo2, dienTich2, mdsd2 -> thua goc 2 (hop) ; tach -> bo
    Select Case LCase$(t)
        Case "sohieuthua2", "tobando2", "dientich2", "mdsd2"
            If mGoc.Count < 2 Then bo = True: Exit Function
            Set v = mGoc.Item(2)
            Select Case LCase$(t)
                Case "sohieuthua2": TH_ThayChu = v.soThua
                Case "tobando2": TH_ThayChu = mTo
                Case "dientich2": TH_ThayChu = SoDt(v.dt)
                Case "mdsd2": TH_ThayChu = v.loaiDat
            End Select
            Exit Function
    End Select

    ' I. Hinh thuc
    If t = "T" & ChrW(225) & "ch th" & ChrW(7917) & "a" Or t = "H" & ChrW(7907) & "p th" & ChrW(7917) & "a" Then
        If gTHCheDo = 2 Then TH_ThayChu = "H" & ChrW(7907) & "p th" & ChrW(7917) & "a" Else TH_ThayChu = "T" & ChrW(225) & "ch th" & ChrW(7917) & "a"
        Exit Function
    End If

    ' II. Thua dat goc
    If batDau(t, "1.1. Th" & ChrW(7917) & "a s" & ChrW(7889) & ":") Then
        TH_ThayChu = DongThuaGoc("1.1.", mGoc.Item(1)): Exit Function
    End If
    If batDau(t, "2.1. Th" & ChrW(7917) & "a s" & ChrW(7889) & ":") Then
        If gTHCheDo = 2 And mGoc.Count >= 2 Then TH_ThayChu = DongThuaGoc("2.1.", mGoc.Item(2))
        Exit Function
    End If
    If InStr(t, "diaChiThuaXHT") > 0 Then
        TH_ThayChu = Replace(s, "diaChiThuaXHT", mDiaChi): Exit Function
    End If
    If t = ChrW(273) & ChrW(7883) & "a ch" & ChrW(7881) & " th" & ChrW(7917) & "a " & ChrW(273) & ChrW(7845) & "t:" Then
        If gTHCheDo = 2 And mGoc.Count >= 2 Then TH_ThayChu = s & " " & mDiaChi
        Exit Function
    End If
    If InStr(t, "chuSuDung") > 0 Then
        TH_ThayChu = Replace(Replace(s, "chuSuDung ,", mGoc.Item(1).TenChu), "chuSuDung", mGoc.Item(1).TenChu)
        Exit Function
    End If
    If InStr(t, "soGiayTo") > 0 Or InStr(t, "diaChiChu") > 0 Then
        TH_ThayChu = Replace(Replace(s, "soGiayTo", "..............."), "diaChiChu", mGoc.Item(1).DiaChi)
        Exit Function
    End If
    If t = "2.2. T" & ChrW(234) & "n ng" & ChrW(432) & ChrW(7901) & "i s" & ChrW(7917) & " d" & ChrW(7909) & "ng " & ChrW(273) & ChrW(7845) & "t:" Then
        If gTHCheDo = 2 And mGoc.Count >= 2 Then TH_ThayChu = s & " " & mGoc.Item(2).TenChu
        Exit Function
    End If
    If batDau(t, "Gi" & ChrW(7845) & "y t" & ChrW(7901) & " nh" & ChrW(226) & "n th" & ChrW(226) & "n/ph" & ChrW(225) & "p nh" & ChrW(226) & "n s" & ChrW(7889) & ":") Then
        If gTHCheDo = 2 And mGoc.Count >= 2 Then TH_ThayChu = "Gi" & ChrW(7845) & "y t" & ChrW(7901) & " nh" & ChrW(226) & "n th" & ChrW(226) & "n/ph" & ChrW(225) & "p nh" & ChrW(226) & "n s" & ChrW(7889) & ": ..............., " & ChrW(273) & ChrW(7883) & "a ch" & ChrW(7881) & ": " & mGoc.Item(2).DiaChi
        Exit Function
    End If

    ' SUA 21/10: mau TT26 moi - "a) Thua so: , to ban do so: toBanDo, dien tich: tongDienTich m2, loai dat:"
    If LaDongThuaSo(t) Then
        ' SUA 22/10: thua thu may theo tieu de "2. Thua dat thu hai" (neu co)
        If mCoY2 Then
            If y < mY2 Then k = 2 Else k = 1
        Else
            k = HangTren(mAY, mNA, y)
        End If
        If k >= 1 And k <= mGoc.Count And (k = 1 Or gTHCheDo = 2) Then
            Set v = mGoc.Item(k)
            TH_ThayChu = Left$(t, InStr(t, "Th" & ChrW(7917) & "a s" & ChrW(7889)) - 1) & "Th" & ChrW(7917) & "a s" & ChrW(7889) & ": " & v.soThua & ", t" & ChrW(7901) & " b" & ChrW(7843) & "n " & ChrW(273) & ChrW(7891) & " s" & ChrW(7889) & ": " & mTo & ", di" & ChrW(7879) & "n t" & ChrW(237) & "ch: " & SoDt(v.dt) & " m" & ChrW(178) & ", lo" & ChrW(7841) & "i " & ChrW(273) & ChrW(7845) & "t: " & v.loaiDat
        Else
            TH_ThayChu = Replace(Replace(s, "toBanDo", "......"), "tongDienTich", "......")
        End If
        Exit Function
    End If
    If LaTieuDeMoi(t) Then
        k = HangTren(mH2Y, mNH2, y)
        If k < 1 Or k > mSau.Count Then bo = True: Exit Function
        TH_ThayChu = "- Th" & ChrW(7917) & "a " & mSau.Item(k).soThua & ":"
        Exit Function
    End If
    If batDau(t, "+ T" & ChrW(7915) & " " & ChrW(273) & "i" & ChrW(7875) & "m") Then
        k = HangGanTren(mH2Y, mNH2, y)
        If k < 1 Or k > mSau.Count Or Not LaDongDauMoi(y) Then bo = True: Exit Function
        cd = "......................"
        If InStr(t, " l" & ChrW(224) & ":") > 0 Then cd = Trim$(Mid$(t, InStr(t, " l" & ChrW(224) & ":") + 4))
        TH_ThayChu = "+ T" & ChrW(7915) & " " & ChrW(273) & "i" & ChrW(7875) & "m " & DsDinhVong(mSau.Item(k)) & " l" & ChrW(224) & ": " & cd
        Exit Function
    End If

    ' III. Thua sau khi tach: "Thua thu nhat: dien tich: ... ; loai dat: ... ; de ..."
    k = ThuTuThua(t)
    If k > 0 Then
        If k > mSau.Count Then bo = True: Exit Function
        Set v = mSau.Item(k)
        cd = ""
        If InStrRev(t, ";") > 0 Then cd = Trim$(Mid$(t, InStrRev(t, ";") + 1))
        If Len(cd) = 0 Then cd = ChrW(273) & ChrW(7875) & " s" & ChrW(7917) & " d" & ChrW(7909) & "ng"
        TH_ThayChu = Left$(t, InStr(t, ":")) & " (" & v.soThua & ") di" & ChrW(7879) & "n t" & ChrW(237) & "ch: " & SoDt(v.dt) & " m" & ChrW(178) & "; lo" & ChrW(7841) & "i " & ChrW(273) & ChrW(7845) & "t: " & v.loaiDat & "; " & cd
        Exit Function
    End If
    If batDau(t, "H" & ChrW(7907) & "p th" & ChrW(224) & "nh th" & ChrW(7917) & "a " & ChrW(273) & ChrW(7845) & "t m" & ChrW(7899) & "i:") Then
        Set v = mSau.Item(1)
        TH_ThayChu = "H" & ChrW(7907) & "p th" & ChrW(224) & "nh th" & ChrW(7917) & "a " & ChrW(273) & ChrW(7845) & "t m" & ChrW(7899) & "i (" & v.soThua & "): di" & ChrW(7879) & "n t" & ChrW(237) & "ch: " & SoDt(v.dt) & " m" & ChrW(178) & ", lo" & ChrW(7841) & "i " & ChrW(273) & ChrW(7845) & "t: " & v.loaiDat & ", " & ChrW(273) & ChrW(7875) & " s" & ChrW(7917) & " d" & ChrW(7909) & "ng"
        Exit Function
    End If

    ' 3.4 Mo ta
    If batDau(t, "- " & ChrW(272) & "i" & ChrW(7875) & "m ") Then
        cd = DsDinhPhay()
        If Len(cd) = 0 Then bo = True Else TH_ThayChu = "- " & ChrW(272) & "i" & ChrW(7875) & "m " & cd & " l" & ChrW(224) & ": ......................"
        Exit Function
    End If
    k = SoMuc34(t)
    If k > 0 Then
        If k > mSau.Count Then bo = True: Exit Function
        TH_ThayChu = "3.4." & k & " Th" & ChrW(7917) & "a " & mSau.Item(k).soThua & ":"
        Exit Function
    End If
    If batDau(t, "- T" & ChrW(7915) & " " & ChrW(273) & "i" & ChrW(7875) & "m") Then
        k = MucCuaDong(y)
        If k <= 0 Or k > mSau.Count Or Not LaDongDau(y) Then bo = True: Exit Function
        TH_ThayChu = "- T" & ChrW(7915) & " " & ChrW(273) & "i" & ChrW(7875) & "m " & DsDinhVong(mSau.Item(k)) & " l" & ChrW(224) & ": ......................"
        Exit Function
    End If

    ' IV. Xac nhan: "- Thua dat du kien (10-1) thanh thua 505."
    If batDau(t, "- Th" & ChrW(7917) & "a " & ChrW(273) & ChrW(7845) & "t d" & ChrW(7921) & " ki" & ChrW(7871) & "n") Then
        Dim p1 As Long, p2 As Long, trong As String
        p1 = InStr(t, "("): p2 = InStr(t, ")")
        If p1 > 0 And p2 > p1 Then trong = Mid$(t, p1 + 1, p2 - p1 - 1)
        If InStr(trong, "+") > 0 Then
            If gTHCheDo <> 2 Then bo = True: Exit Function
            TH_ThayChu = "- Th" & ChrW(7917) & "a " & ChrW(273) & ChrW(7845) & "t d" & ChrW(7921) & " ki" & ChrW(7871) & "n (" & mSau.Item(1).soThua & ") th" & ChrW(224) & "nh th" & ChrW(7917) & "a ..........."
        Else
            If gTHCheDo = 2 Then bo = True: Exit Function
            k = CLng(val(Mid$(trong, InStr(trong, "-") + 1)))
            If k < 1 Or k > mSau.Count Then bo = True: Exit Function
            TH_ThayChu = "- Th" & ChrW(7917) & "a " & ChrW(273) & ChrW(7845) & "t d" & ChrW(7921) & " ki" & ChrW(7871) & "n (" & mSau.Item(k).soThua & ") th" & ChrW(224) & "nh th" & ChrW(7917) & "a ..........."
        End If
        Exit Function
    End If
End Function

' SUA 21/10: dong "... Thua so: ..., to ban do so: ..." (mau TT26 moi)
Private Function LaDongThuaSo(ByVal t As String) As Boolean
    LaDongThuaSo = (InStr(t, "Th" & ChrW(7917) & "a s" & ChrW(7889)) > 0 And InStr(t, "t" & ChrW(7901) & " b" & ChrW(7843) & "n " & ChrW(273) & ChrW(7891)) > 0)
End Function

' SUA 21/10: "- Thua 161-1:" (khong phai "- Thua dat ...")
Private Function LaTieuDeMoi(ByVal t As String) As Boolean
    t = Trim$(t)
    If Left$(t, 7) <> "- Th" & ChrW(7917) & "a " Then Exit Function
    If Left$(t, 10) = "- Th" & ChrW(7917) & "a " & ChrW(273) & ChrW(7845) & "t" Then Exit Function
    LaTieuDeMoi = (Right$(t, 1) = ":")
End Function

' thu tu (tu tren xuong) cua dong o do cao y trong danh sach ys
Private Function HangTren(ys() As Double, ByVal n As Long, ByVal y As Double) As Long
    Dim i As Long
    HangTren = 1
    For i = 1 To n
        If ys(i) > y + 0.001 Then HangTren = HangTren + 1
    Next i
End Function

' thu tu cua tieu de gan nhat phia tren y (0 neu khong co)
Private Function HangGanTren(ys() As Double, ByVal n As Long, ByVal y As Double) As Long
    Dim i As Long, yB As Double
    yB = 1E+30
    For i = 1 To n
        If ys(i) > y And ys(i) < yB Then yB = ys(i)
    Next i
    If yB < 1E+29 Then HangGanTren = HangTren(ys, n, yB)
End Function

' dong "+ Tu diem" dau tien ngay duoi tieu de "- Thua x:"
Private Function LaDongDauMoi(ByVal y As Double) As Boolean
    Dim i As Long, yHd As Double
    yHd = 1E+30
    For i = 1 To mNH2
        If mH2Y(i) > y And mH2Y(i) < yHd Then yHd = mH2Y(i)
    Next i
    If yHd > 1E+29 Then Exit Function
    For i = 1 To mNTu
        If mTuY(i) > y + 0.001 And mTuY(i) < yHd Then Exit Function
    Next i
    LaDongDauMoi = True
End Function

Private Function batDau(ByVal t As String, ByVal dau As String) As Boolean
    batDau = (Left$(t, Len(dau)) = dau)
End Function

Private Function DongThuaGoc(ByVal Muc As String, ByVal v As clsVung) As String
    DongThuaGoc = Muc & " Th" & ChrW(7917) & "a s" & ChrW(7889) & ": " & v.soThua & ", t" & ChrW(7901) & " b" & ChrW(7843) & "n " & ChrW(273) & ChrW(7891) & " s" & ChrW(7889) & ": " & mTo & ", di" & ChrW(7879) & "n t" & ChrW(237) & "ch: " & _
                  SoDt(v.dt) & " m" & ChrW(178) & ", lo" & ChrW(7841) & "i " & ChrW(273) & ChrW(7845) & "t: " & v.loaiDat
End Function

' "Thua thu nhat:" -> 1 ... "Thua thu tu:" -> 4 (0 neu khong phai)
Private Function ThuTuThua(ByVal t As String) As Long
    Dim dS As Variant, i As Long
    dS = Array("nh" & ChrW(7845) & "t", "hai", "ba", "t" & ChrW(432), "n" & ChrW(259) & "m", "s" & ChrW(225) & "u", "b" & ChrW(7843) & "y", "t" & ChrW(225) & "m", "ch" & ChrW(237) & "n", "m" & ChrW(432) & ChrW(7901) & "i")
    For i = 0 To UBound(dS)
        If Left$(t, Len("Th" & ChrW(7917) & "a th" & ChrW(7913) & " " & dS(i) & ":")) = "Th" & ChrW(7917) & "a th" & ChrW(7913) & " " & dS(i) & ":" Then ThuTuThua = i + 1: Exit Function
    Next i
End Function

' "3.4.2 Thua 161-2:" -> 2
Private Function SoMuc34(ByVal t As String) As Long
    If Left$(t, 4) <> "3.4." Then Exit Function
    If InStr(t, "Th" & ChrW(7917) & "a") = 0 Then Exit Function
    SoMuc34 = CLng(val(Mid$(t, 5)))
End Function

' Muc 3.4.k chua dong o do cao y (dong tieu de gan nhat phia tren)
Private Function MucCuaDong(ByVal y As Double) As Long
    Dim i As Long, yBest As Double
    yBest = 1E+30
    For i = 1 To mNHd
        If mHdY(i) > y And mHdY(i) < yBest Then yBest = mHdY(i): MucCuaDong = mHdK(i)
    Next i
End Function

' Dong "- Tu diem" dau tien ngay duoi tieu de cua no
Private Function LaDongDau(ByVal y As Double) As Boolean
    Dim i As Long, yHd As Double
    yHd = 1E+30
    For i = 1 To mNHd
        If mHdY(i) > y And mHdY(i) < yHd Then yHd = mHdY(i)
    Next i
    For i = 1 To mNTu
        If mTuY(i) > y And mTuY(i) < yHd Then Exit Function      ' co dong khac cao hon
    Next i
    LaDongDau = True
End Function

' "1',2',3'" - tat ca dinh so do SAU
Private Function DsDinhPhay() As String
    Dim n As Long, i As Long, s As String
    If mSoS Is Nothing Then Exit Function
    n = mSoS.Count
    For i = 1 To n
        If Len(s) > 0 Then s = s & ","
        s = s & i & "'"
    Next i
    DsDinhPhay = s
End Function

' "1 den diem 2-3'-4'-1"
Private Function DsDinhVong(ByVal v As clsVung) As String
    Dim rg() As Double, i As Long, m As Long, s As String
    rg = v.ring: m = UBound(rg, 1)
    s = TH_SoDinh(rg(0, 0), rg(0, 1)) & " " & ChrW(273) & ChrW(7871) & "n " & ChrW(273) & "i" & ChrW(7875) & "m "
    For i = 1 To m
        If i > 1 Then s = s & "-"
        s = s & TH_SoDinh(rg(i, 0), rg(i, 1))
    Next i
    DsDinhVong = s
End Function

'============================================================
' Tien ich
'============================================================
Private Function SoDt(ByVal d As Double) As String
    SoDt = Replace(Format$(Round(d, 1), "0.0"), ".", ",")
End Function

Private Function DiaChiThua(ByVal xa As String, ByVal huyen As String, ByVal tinh As String) As String
    Dim s As String
    If Len(Trim$(xa)) > 0 Then s = Trim$(xa)
    If Len(Trim$(huyen)) > 0 Then s = s & IIf(Len(s) > 0, ", ", "") & Trim$(huyen)
    If Len(Trim$(tinh)) > 0 Then s = s & IIf(Len(s) > 0, ", ", "") & Trim$(tinh)
    DiaChiThua = s
End Function

Public Function TH_DienTich(ByVal v As clsVung) As Double
    Dim rg() As Double, s As Double, k As Long
    rg = v.ring
    s = Abs(DtRing(rg))
    For k = 1 To v.dao.Count
        rg = v.dao.Item(k)
        s = s - Abs(DtRing(rg))
    Next k
    TH_DienTich = s
End Function

Private Function DtRing(rg() As Double) As Double
    Dim i As Long, s As Double
    For i = 0 To UBound(rg, 1) - 1
        s = s + rg(i, 0) * rg(i + 1, 1) - rg(i + 1, 0) * rg(i, 1)
    Next i
    DtRing = s / 2#
End Function

Public Sub BaoRing(rg() As Double, ByRef x1 As Double, ByRef y1 As Double, _
                   ByRef x2 As Double, ByRef y2 As Double)
    Dim i As Long
    x1 = rg(0, 0): x2 = x1: y1 = rg(0, 1): y2 = y1
    For i = 0 To UBound(rg, 1)
        If rg(i, 0) < x1 Then x1 = rg(i, 0)
        If rg(i, 0) > x2 Then x2 = rg(i, 0)
        If rg(i, 1) < y1 Then y1 = rg(i, 1)
        If rg(i, 1) > y2 Then y2 = rg(i, 1)
    Next i
End Sub

' Sap thua: theo hang (tren xuong, sai lech y < tolY coi nhu cung hang), trai sang phai
Private Function SapDocDoc(ByVal dS As Collection, ByVal tolY As Double) As Collection
    Dim n As Long, i As Long, j As Long, a() As clsVung, tmp As clsVung, truoc As Boolean
    n = dS.Count
    ReDim a(1 To n)
    For i = 1 To n
        Set a(i) = dS.Item(i)
    Next i
    For i = 2 To n
        Set tmp = a(i): j = i - 1
        Do While j >= 1
            If Abs(a(j).cy - tmp.cy) > tolY Then truoc = (a(j).cy < tmp.cy) Else truoc = (a(j).cx > tmp.cx)
            If Not truoc Then Exit Do
            Set a(j + 1) = a(j): j = j - 1
        Loop
        Set a(j + 1) = tmp
    Next i
    Dim kq As New Collection
    For i = 1 To n
        kq.Add a(i)
    Next i
    Set SapDocDoc = kq
End Function

' SUA 22/10: HOP thua - ve canh chung giua cac thua da chon (net dut) tren so do SAU
'   (goi tu modKhungMau.ChenKhungTachHop). Toa do: P' = (P - g) * kp + o
Public Sub TH_VeRanhChung(ByVal ox As Double, ByVal oy As Double, ByVal gx As Double, _
                          ByVal gy As Double, ByVal kp As Double)
    Dim i As Long, s() As Double, le As LineElement, ls As LineStyle
    If mChung Is Nothing Then Exit Sub
    On Error Resume Next
    Set ls = ActiveDesignFile.LineStyles.Find("2")
    For i = 1 To mChung.Count
        s = mChung.Item(i)
        Set le = Nothing
        Set le = CreateLineElement2(Nothing, Point3dFromXYZ(ox + (s(0) - gx) * kp, oy + (s(1) - gy) * kp, 0#), _
                                    Point3dFromXYZ(ox + (s(2) - gx) * kp, oy + (s(3) - gy) * kp, 0#))
        If Not le Is Nothing Then
            If Not ls Is Nothing Then Set le.LineStyle = ls
            le.LineWeight = 0
            ActiveModelReference.AddElement le
        End If
    Next i
    Err.Clear
End Sub

' SUA 28/10: bang phu "So hieu dinh thua | Chieu dai (m)" (tag tths/cdhs) = chep tu bang
'   "Doan | Chieu dai" (so do SAU), BO dau ' : 1'-2' 5,00 ; 2'-3' ... -> dinh 1,2,3...,1
'   Chi lay chuoi doan lien tiep dau tien (ranh ngoai). Tra ve so hang (0 = khong co).
Public Function TH_BangPhu(rSo() As String, rCanh() As Double, rx() As Double, ry() As Double) As Long
    Dim n As Long, i As Long, e As Variant, a As String, b As String, truoc As String
    On Error GoTo Thoi
    If mDoanS Is Nothing Then Exit Function
    If mDoanS.Count = 0 Then Exit Function
    ReDim rSo(1 To mDoanS.Count + 1): ReDim rCanh(1 To mDoanS.Count + 1)
    ReDim rx(1 To mDoanS.Count + 1): ReDim ry(1 To mDoanS.Count + 1)
    For i = 1 To mDoanS.Count
        e = mDoanS.Item(i)
        a = Replace(CStr(e(0)), "'", ""): b = Replace(CStr(e(1)), "'", "")
        If n > 0 And a <> truoc Then Exit For          ' het chuoi ranh ngoai
        If n = 0 Then n = 1: rSo(1) = a
        rCanh(n) = CDbl(e(2))
        n = n + 1: rSo(n) = b: rCanh(n) = -1#
        truoc = b
    Next i
    If n < 2 Then Exit Function
    TH_BangPhu = n
Thoi:
End Function

Attribute VB_Name = "modTachLop"
'============================================================
' modTachLop - Tach lop nhan thua: chu chung 1 lop -> 3 lop
'   Co chu cai (LUK, ONT...)        -> lop loai dat
'   Chi chu so (2248)               -> lop so thua
'   So co dau phay/cham (4846,2)    -> lop dien tich
'   Con lai (12+13, -, ...)         -> giu nguyen
'   Form: frmTachLop (tu tao). Menu Tien ich -> "TACHLOP".
'============================================================
Option Explicit

Private mDs As Collection       ' phan tu se chuyen
Private mLoai As Collection     ' loai tuong ung (1/2/3)

Public Sub DC_MoTachLop()
    DC_MoFormTuTao "frmTachLop"
End Sub

' 0 = bo qua ; 1 = loai dat ; 2 = so thua ; 3 = dien tich
Public Function TL_PhanLoai(ByVal s As String) As Long
    Dim i As Long, c As Long, coChu As Boolean, nSo As Long, coPhay As Boolean, khac As Boolean
    s = Trim$(s)
    If Len(s) = 0 Then Exit Function
    For i = 1 To Len(s)
        c = AscW(Mid$(s, i, 1)) And &HFFFF&
        If (c >= 65 And c <= 90) Or (c >= 97 And c <= 122) Or c >= 128 Then
            coChu = True
        ElseIf c >= 48 And c <= 57 Then
            nSo = nSo + 1
        ElseIf c = 44 Or c = 46 Then
            coPhay = True
        ElseIf c <> 32 Then
            khac = True
        End If
    Next i
    If coChu Then TL_PhanLoai = 1: Exit Function
    If nSo = 0 Or khac Then Exit Function
    If coPhay Then TL_PhanLoai = 3 Else TL_PhanLoai = 2
End Function

Private Function noiDung(ByVal el As Element) As String
    Dim subs As ElementEnumerator, s As String
    On Error Resume Next
    If el.Type = msdElementTypeText Then
        noiDung = el.AsTextElement.Text
    ElseIf el.Type = msdElementTypeTextNode Then
        Set subs = el.AsComplexElement.GetSubElements
        Do While subs.MoveNext
            If subs.Current.Type = msdElementTypeText Then s = s & " " & subs.Current.AsTextElement.Text
        Loop
        noiDung = Trim$(s)
    End If
End Function

' Buoc 1: quet + phan loai (file hien tai). Tra ve so phan tu tung loai (n(1..3)), nBo = so chu giu nguyen.
Public Function TL_Quet(ByVal lvNguon As Long, ByVal chiChon As Boolean, ByRef n() As Long, ByRef nBo As Long) As Long
    Dim ee As ElementEnumerator
    Set mDs = New Collection
    Set mLoai = New Collection
    ReDim n(0 To 3)
    nBo = 0
    On Error Resume Next
    If chiChon Then
        Set ee = ActiveModelReference.GetSelectedElements
    Else
        Set ee = QuetChu(ActiveModelReference)
    End If
    If ee Is Nothing Then Exit Function
    GomPhanLoai ee, lvNguon, mDs, mLoai, n, nBo
    TL_Quet = mDs.Count
End Function

Private Function QuetChu(ByVal m As ModelReference) As ElementEnumerator
    Dim esc As ElementScanCriteria
    On Error Resume Next
    Set esc = New ElementScanCriteria
    esc.ExcludeAllTypes
    esc.IncludeType msdElementTypeText
    esc.IncludeType msdElementTypeTextNode
    Set QuetChu = m.Scan(esc)
End Function

Private Sub GomPhanLoai(ByVal ee As ElementEnumerator, ByVal lvNguon As Long, ByVal dS As Collection, _
                        ByVal loai As Collection, ByRef n() As Long, ByRef nBo As Long)
    Dim el As Element, k As Long
    If ee Is Nothing Then Exit Sub
    On Error Resume Next
    Do While ee.MoveNext
        Set el = ee.Current
        If el.Type = msdElementTypeText Or el.Type = msdElementTypeTextNode Then
            If DC_LevelSo(el) = lvNguon Then
                k = TL_PhanLoai(noiDung(el))
                If k > 0 Then
                    dS.Add el
                    loai.Add k
                    n(k) = n(k) + 1
                Else
                    nBo = nBo + 1
                End If
            End If
        End If
    Loop
End Sub

' Buoc 2: chuyen lop (file hien tai, sau TL_Quet). lv(1..3) = so level dich (<= 0 : khong chuyen loai do)
Public Function TL_Chuyen(ByRef lv() As Long, ByRef nDa() As Long) As Long
    ReDim nDa(0 To 3)
    If mDs Is Nothing Then Exit Function
    TL_Chuyen = ChuyenDs(ActiveDesignFile, mDs, mLoai, lv, nDa)
    Set mDs = Nothing
    Set mLoai = Nothing
    RedrawAllViews
End Function

Private Function ChuyenDs(ByVal df As DesignFile, ByVal dS As Collection, ByVal loai As Collection, _
                          ByRef lv() As Long, ByRef nDa() As Long) As Long
    Dim i As Long, k As Long, el As Element, lvObj(1 To 3) As Level
    For k = 1 To 3
        If lv(k) > 0 Then Set lvObj(k) = LvTheoSo(df, lv(k))
    Next k
    On Error Resume Next
    For i = 1 To dS.Count
        k = loai.Item(i)
        If Not lvObj(k) Is Nothing Then
            Set el = dS.Item(i)
            Err.Clear
            Set el.Level = lvObj(k)
            If Err.Number <> 0 Then Err.Clear: el.Level = lvObj(k)
            el.Rewrite
            If Err.Number = 0 Then nDa(k) = nDa(k) + 1: ChuyenDs = ChuyenDs + 1
        End If
    Next i
End Function

' Level theo SO trong 1 design file; chua co thi tao "Level n"
Private Function LvTheoSo(ByVal df As DesignFile, ByVal n As Long) As Level
    Dim lv As Level
    On Error Resume Next
    For Each lv In df.Levels
        If lv.Number = n Then Set LvTheoSo = lv: Exit Function
    Next lv
    Set lv = df.AddNewLevel("Level " & n)
    If Not lv Is Nothing Then
        lv.Number = n
        df.Levels.Rewrite
        Set LvTheoSo = lv
    End If
End Function

'============================================================
' HANG LOAT: tach lop 1 file (mo ngam -> sua -> Save -> Close)
'   Tra ve "" neu OK; nDa(1..3) = so chu da chuyen tung loai.
'============================================================
Public Function TL_XuLyFile(ByVal path As String, ByVal lvNguon As Long, ByRef lv() As Long, _
                            ByVal saoLuu As Boolean, ByRef nDa() As Long) As String
    Dim df As DesignFile, laHienTai As Boolean, m As ModelReference
    Dim dS As Collection, loai As Collection, n() As Long, nBo As Long, tong As Long, k As Long
    ReDim nDa(0 To 3)
    On Error Resume Next
    laHienTai = (StrComp(ActiveDesignFile.FullName, path, vbTextCompare) = 0)
    Err.Clear
    If saoLuu Then
        Dim fso As Object
        Set fso = CreateObject("Scripting.FileSystemObject")
        fso.CopyFile path, path & ".bak", True
        If Err.Number <> 0 Then
            TL_XuLyFile = "Kh" & ChrW(244) & "ng sao l" & ChrW(432) & "u " & ChrW(273) & ChrW(432) & ChrW(7907) & "c (.bak): " & Err.Description
            Exit Function
        End If
    End If

    On Error GoTo Loi
    If laHienTai Then
        Set df = ActiveDesignFile
    Else
        Set df = Application.OpenDesignFileForProgram(path, False)
    End If
    If df Is Nothing Then TL_XuLyFile = "Kh" & ChrW(244) & "ng m" & ChrW(7903) & " " & ChrW(273) & ChrW(432) & ChrW(7907) & "c file": Exit Function

    Dim d() As Long
    For Each m In df.Models
        Set dS = New Collection: Set loai = New Collection
        ReDim n(0 To 3): nBo = 0
        GomPhanLoai QuetChu(m), lvNguon, dS, loai, n, nBo
        If dS.Count > 0 Then
            ReDim d(0 To 3)
            tong = tong + ChuyenDs(df, dS, loai, lv, d)
            For k = 1 To 3
                nDa(k) = nDa(k) + d(k)
            Next k
        End If
    Next m
    If tong > 0 Then df.Save
    If Not laHienTai Then df.Close
    Exit Function
Loi:
    TL_XuLyFile = Err.Description
    On Error Resume Next
    If Not laHienTai Then
        If Not df Is Nothing Then df.Close
    End If
End Function

'============================================================
' PHA KHOI (drop cell) co chua chu tren lop can tach
'   Cell thuong: chep cac phan tu con (Clone) ra ngoai roi xoa cell.
'   Shared cell: chua pha duoc bang VBA -> chi dem de bao.
'   lvNguon <= 0 : khoi co chu o bat ky lop nao.
'============================================================
Public Function TL_PhaKhoiFile(ByVal path As String, ByVal lvNguon As Long, ByVal saoLuu As Boolean, _
                               ByVal chiChon As Boolean, ByRef nPha As Long, ByRef nShared As Long) As String
    Dim df As DesignFile, laHienTai As Boolean, m As ModelReference
    nPha = 0: nShared = 0
    On Error Resume Next
    laHienTai = (StrComp(ActiveDesignFile.FullName, path, vbTextCompare) = 0)
    Err.Clear
    If saoLuu And Not laHienTai Then
        Dim fso As Object
        Set fso = CreateObject("Scripting.FileSystemObject")
        fso.CopyFile path, path & ".bak", True
        If Err.Number <> 0 Then
            TL_PhaKhoiFile = "Kh" & ChrW(244) & "ng sao l" & ChrW(432) & "u " & ChrW(273) & ChrW(432) & ChrW(7907) & "c (.bak): " & Err.Description
            Exit Function
        End If
    End If

    On Error GoTo Loi
    If laHienTai Then
        If chiChon Then
            PhaKhoiDs ActiveModelReference, ActiveModelReference.GetSelectedElements, lvNguon, nPha, nShared
            RedrawAllViews
            Exit Function
        End If
        Set df = ActiveDesignFile
    Else
        Set df = Application.OpenDesignFileForProgram(path, False)
    End If
    If df Is Nothing Then TL_PhaKhoiFile = "Kh" & ChrW(244) & "ng m" & ChrW(7903) & " " & ChrW(273) & ChrW(432) & ChrW(7907) & "c file": Exit Function
    For Each m In df.Models
        PhaKhoiDs m, QuetKhoi(m), lvNguon, nPha, nShared
    Next m
    If nPha > 0 Then df.Save
    If Not laHienTai Then df.Close Else RedrawAllViews
    Exit Function
Loi:
    TL_PhaKhoiFile = Err.Description
    On Error Resume Next
    If Not laHienTai Then
        If Not df Is Nothing Then df.Close
    End If
End Function

Private Function QuetKhoi(ByVal m As ModelReference) As ElementEnumerator
    Dim esc As ElementScanCriteria
    On Error Resume Next
    Set esc = New ElementScanCriteria
    esc.ExcludeAllTypes
    esc.IncludeType msdElementTypeCellHeader
    esc.IncludeType msdElementTypeSharedCell
    Set QuetKhoi = m.Scan(esc)
End Function

Private Sub PhaKhoiDs(ByVal m As ModelReference, ByVal ee As ElementEnumerator, ByVal lvNguon As Long, _
                      ByRef nPha As Long, ByRef nShared As Long)
    Dim dS As New Collection, el As Element, i As Long, Loi As Boolean
    If ee Is Nothing Then Exit Sub
    On Error Resume Next
    Do While ee.MoveNext
        Set el = ee.Current
        If el.Type = msdElementTypeSharedCell Then
            nShared = nShared + 1
        ElseIf el.Type = msdElementTypeCellHeader Then
            If KhoiCoChu(el, lvNguon) Then dS.Add el
        End If
    Loop
    For i = 1 To dS.Count
        Set el = dS.Item(i)
        Loi = False
        ChepConKhoi m, el, Loi
        If Not Loi Then
            Err.Clear
            m.RemoveElement el
            If Err.Number = 0 Then nPha = nPha + 1
        End If
    Next i
End Sub

' Khoi co chu (text / text node) tren lop lvNguon (<= 0: lop bat ky), tim ca khoi long nhau
Private Function KhoiCoChu(ByVal el As Element, ByVal lvNguon As Long) As Boolean
    Dim subs As ElementEnumerator, c As Element
    On Error Resume Next
    Set subs = el.AsComplexElement.GetSubElements
    If subs Is Nothing Then Exit Function
    Do While subs.MoveNext
        Set c = subs.Current
        If c.Type = msdElementTypeText Or c.Type = msdElementTypeTextNode Then
            If lvNguon <= 0 Then KhoiCoChu = True: Exit Function
            If DC_LevelSo(c) = lvNguon Then KhoiCoChu = True: Exit Function
        ElseIf c.Type = msdElementTypeCellHeader Then
            If KhoiCoChu(c, lvNguon) Then KhoiCoChu = True: Exit Function
        End If
    Loop
End Function

' Chep cac phan tu con cua khoi ra model (khoi long nhau -> pha tiep)
Private Sub ChepConKhoi(ByVal m As ModelReference, ByVal el As Element, ByRef Loi As Boolean)
    Dim subs As ElementEnumerator, c As Element, cp As Element, o As Object
    On Error Resume Next
    Set subs = el.AsComplexElement.GetSubElements
    If subs Is Nothing Then Loi = True: Exit Sub
    Do While subs.MoveNext
        Set c = subs.Current
        If c.Type = msdElementTypeCellHeader Then
            ChepConKhoi m, c, Loi
        Else
            Err.Clear
            Set cp = Nothing
            Set o = c
            Set cp = o.Clone              ' late binding: thieu Clone -> loi chay (bat duoc), khong loi bien dich
            If Err.Number = 0 And Not cp Is Nothing Then
                m.AddElement cp
                If Err.Number <> 0 Then Loi = True
            Else
                Loi = True
            End If
        End If
    Loop
End Sub

'============================================================
' SUA 25/10: PHA CHU GOP - 1 chu ghi chung "LUC 766/3860,9" -> 3 chu rieng
'   chu cai (LUC, ONT+CLN) = loai dat ; so dau tien = so thua ;
'   so tiep theo (sau khoang trang hoac "/") = dien tich.
'   Chu moi giu font/co/goc xoay/lop cua chu goc, dat dung vi tri tung phan
'   -> sau do bam "Tach lop" de dua ve 3 lop.
'============================================================
Public Function TL_TachChuGopFile(ByVal path As String, ByVal lvNguon As Long, ByVal saoLuu As Boolean, _
                                  ByVal chiChon As Boolean, ByRef nTach As Long) As String
    Dim df As DesignFile, laHienTai As Boolean, m As ModelReference
    nTach = 0
    On Error Resume Next
    laHienTai = (StrComp(ActiveDesignFile.FullName, path, vbTextCompare) = 0)
    Err.Clear
    If saoLuu And Not laHienTai Then
        Dim fso As Object
        Set fso = CreateObject("Scripting.FileSystemObject")
        fso.CopyFile path, path & ".bak", True
        If Err.Number <> 0 Then
            TL_TachChuGopFile = "Kh" & ChrW(244) & "ng sao l" & ChrW(432) & "u " & ChrW(273) & ChrW(432) & ChrW(7907) & "c (.bak): " & Err.Description
            Exit Function
        End If
    End If
    On Error GoTo Loi
    If laHienTai Then
        If chiChon Then
            TachChuDs ActiveModelReference, ActiveModelReference.GetSelectedElements, lvNguon, nTach
            RedrawAllViews
            Exit Function
        End If
        Set df = ActiveDesignFile
    Else
        Set df = Application.OpenDesignFileForProgram(path, False)
    End If
    If df Is Nothing Then TL_TachChuGopFile = "Kh" & ChrW(244) & "ng m" & ChrW(7903) & " " & ChrW(273) & ChrW(432) & ChrW(7907) & "c file": Exit Function
    For Each m In df.Models
        TachChuDs m, QuetChu(m), lvNguon, nTach
    Next m
    If nTach > 0 Then df.Save
    If Not laHienTai Then df.Close Else RedrawAllViews
    Exit Function
Loi:
    TL_TachChuGopFile = Err.Description
    On Error Resume Next
    If Not laHienTai Then
        If Not df Is Nothing Then df.Close
    End If
End Function

' Tach chuoi -> phan (noi dung, vi tri ky tu bat dau). Tra ve so phan (0 = khong phai chu gop)
Public Function TL_TachChuoi(ByVal s As String, ByRef ten() As String, ByRef viTri() As Long) As Long
    Dim i As Long, c As String, tok As String, bd As Long, n As Long
    Dim loai As String, pLoai As Long, so As String, pSo As Long, dt As String, pDt As Long
    Dim toks() As String, pos() As Long, nt As Long
    ReDim toks(1 To 20): ReDim pos(1 To 20)
    s = s & " "
    For i = 1 To Len(s)
        c = Mid$(s, i, 1)
        If c = " " Or c = "/" Or c = vbTab Then
            If Len(tok) > 0 And nt < 20 Then nt = nt + 1: toks(nt) = tok: pos(nt) = bd
            tok = ""
        Else
            If Len(tok) = 0 Then bd = i
            tok = tok & c
        End If
    Next i
    If nt < 2 Then Exit Function
    For i = 1 To nt
        tok = toks(i)
        If LaMaLoai(tok) Then
            If Len(loai) > 0 Or Len(so) > 0 Then Exit Function
            loai = tok: pLoai = pos(i)
        ElseIf LaSo(tok, False) And Len(so) = 0 Then
            so = tok: pSo = pos(i)
        ElseIf LaSo(tok, True) And Len(so) > 0 And Len(dt) = 0 Then
            dt = tok: pDt = pos(i)
        Else
            Exit Function                ' co phan la (vd ten duong) -> khong tach
        End If
    Next i
    If Len(so) = 0 Then Exit Function
    ReDim ten(1 To 3): ReDim viTri(1 To 3)
    If Len(loai) > 0 Then n = n + 1: ten(n) = loai: viTri(n) = pLoai
    n = n + 1: ten(n) = so: viTri(n) = pSo
    If Len(dt) > 0 Then n = n + 1: ten(n) = dt: viTri(n) = pDt
    If n < 2 Then n = 0
    TL_TachChuoi = n
End Function

' Ma loai dat: chu IN HOA A-Z (co the co "+"), dai 2..12
Private Function LaMaLoai(ByVal t As String) As Boolean
    Dim i As Long, c As Long, coChu As Boolean
    If Len(t) < 2 Or Len(t) > 12 Then Exit Function
    For i = 1 To Len(t)
        c = AscW(Mid$(t, i, 1))
        If c >= 65 And c <= 90 Then
            coChu = True
        ElseIf c <> 43 Then
            Exit Function
        End If
    Next i
    LaMaLoai = coChu
End Function

' So: chi chu so ; choPhay = cho phep dau , hoac . (dien tich)
Private Function LaSo(ByVal t As String, ByVal choPhay As Boolean) As Boolean
    Dim i As Long, c As Long, nSo As Long
    For i = 1 To Len(t)
        c = AscW(Mid$(t, i, 1))
        If c >= 48 And c <= 57 Then
            nSo = nSo + 1
        ElseIf choPhay And (c = 44 Or c = 46) Then
        Else
            Exit Function
        End If
    Next i
    LaSo = (nSo > 0)
End Function

Private Sub TachChuDs(ByVal m As ModelReference, ByVal ee As ElementEnumerator, ByVal lvNguon As Long, ByRef nTach As Long)
    Dim dS As New Collection, el As Element, c As Element, i As Long
    If ee Is Nothing Then Exit Sub
    On Error Resume Next
    Do While ee.MoveNext
        Set el = ee.Current
        If el.Type = msdElementTypeText Or el.Type = msdElementTypeTextNode Then
            If lvNguon <= 0 Or DC_LevelSo(el) = lvNguon Then dS.Add el
        End If
    Loop
    For i = 1 To dS.Count
        Set el = dS.Item(i)
        Set c = ChuDon(el)
        If Not c Is Nothing Then
            If TachMotChu(m, el, c) Then nTach = nTach + 1
        End If
    Next i
End Sub

' Text -> chinh no ; text node 1 dong -> chu con ; con lai Nothing
Private Function ChuDon(ByVal el As Element) As Element
    Dim sb As ElementEnumerator, dem As Long, c As Element
    On Error Resume Next
    If el.Type = msdElementTypeText Then Set ChuDon = el: Exit Function
    Set sb = el.AsComplexElement.GetSubElements
    Do While sb.MoveNext
        If sb.Current.Type = msdElementTypeText Then dem = dem + 1: Set c = sb.Current
    Loop
    If dem = 1 Then Set ChuDon = c
End Function

Private Function TachMotChu(ByVal m As ModelReference, ByVal el As Element, ByVal c As Element) As Boolean
    Dim s As String, ten() As String, vt() As Long, n As Long, i As Long
    Dim te As TextElement, rot As Matrix3d, d As Point3d, h As Double
    Dim rw As Double, rh As Double, L As Double, ca As Double, sa As Double
    Dim cx As Double, cy As Double, f As Double, nt As TextElement, ts As Object
    On Error Resume Next
    Set te = c
    s = te.Text
    n = TL_TachChuoi(s, ten, vt)
    If n < 2 Then Exit Function
    rot = te.Rotation
    d.x = rot.RowX.x: d.y = rot.RowY.x: d.Z = 0#      ' truc X cua chu sau khi xoay
    If Err.Number <> 0 Then Err.Clear: d = Point3dFromXYZ(1#, 0#, 0#)
    L = Sqr(d.x * d.x + d.y * d.y): If L <= 0 Then d = Point3dFromXYZ(1#, 0#, 0#): L = 1#
    d.x = d.x / L: d.y = d.y / L
    h = te.TextStyle.Height
    rw = el.Range.High.x - el.Range.Low.x: rh = el.Range.High.y - el.Range.Low.y
    cx = (el.Range.High.x + el.Range.Low.x) / 2#: cy = (el.Range.High.y + el.Range.Low.y) / 2#
    ca = Abs(d.x): sa = Abs(d.y)
    If ca >= sa Then L = (rw - h * sa) / ca Else L = (rh - h * ca) / sa
    If L <= 0 Then L = Len(s) * h * 0.6
    Dim moi As New Collection
    For i = 1 To n
        f = (vt(i) - 1 + Len(ten(i)) / 2#) / Len(s)
        Set nt = Nothing
        Set nt = CreateTextElement1(c, ten(i), Point3dFromXYZ(cx + d.x * (f - 0.5) * L, cy + d.y * (f - 0.5) * L, 0#), rot)
        If nt Is Nothing Then Exit Function
        Set ts = nt.TextStyle
        ts.Justification = msdTextJustificationCenterCenter
        Set nt.TextStyle = ts
        Err.Clear
        nt.color = c.color
        moi.Add nt
    Next i
    Err.Clear
    For i = 1 To moi.Count
        m.AddElement moi.Item(i)
    Next i
    If Err.Number <> 0 Then Exit Function
    m.RemoveElement el
    TachMotChu = (Err.Number = 0)
    Err.Clear
End Function

'============================================================
' SUA 05/11: XOA CHU TRUNG - chu cung noi dung, cung lop, nam chong len nhau
'   (copy/dan 2 lan). Giu 1 chu (chu ve truoc), xoa cac chu sau.
'   lvNguon <= 0 : moi lop ; tol = khoang cach tam toi da (m)
'============================================================
Public Function TL_XoaTrungFile(ByVal path As String, ByVal lvNguon As Long, ByVal saoLuu As Boolean, _
                                ByVal chiChon As Boolean, ByVal tol As Double, ByRef nXoa As Long) As String
    Dim df As DesignFile, laHienTai As Boolean, m As ModelReference
    nXoa = 0
    If tol <= 0 Then tol = 0.2
    On Error Resume Next
    laHienTai = (StrComp(ActiveDesignFile.FullName, path, vbTextCompare) = 0)
    Err.Clear
    If saoLuu And Not laHienTai Then
        Dim fso As Object
        Set fso = CreateObject("Scripting.FileSystemObject")
        fso.CopyFile path, path & ".bak", True
        If Err.Number <> 0 Then
            TL_XoaTrungFile = "Kh" & ChrW(244) & "ng sao l" & ChrW(432) & "u " & ChrW(273) & ChrW(432) & ChrW(7907) & "c (.bak): " & Err.Description
            Exit Function
        End If
    End If
    On Error GoTo Loi
    If laHienTai Then
        If chiChon Then
            XoaTrungDs ActiveModelReference, ActiveModelReference.GetSelectedElements, lvNguon, tol, nXoa
            RedrawAllViews
            Exit Function
        End If
        Set df = ActiveDesignFile
    Else
        Set df = Application.OpenDesignFileForProgram(path, False)
    End If
    If df Is Nothing Then TL_XoaTrungFile = "Kh" & ChrW(244) & "ng m" & ChrW(7903) & " " & ChrW(273) & ChrW(432) & ChrW(7907) & "c file": Exit Function
    For Each m In df.Models
        XoaTrungDs m, QuetChu(m), lvNguon, tol, nXoa
    Next m
    If nXoa > 0 Then df.Save
    If Not laHienTai Then df.Close Else RedrawAllViews
    Exit Function
Loi:
    TL_XoaTrungFile = Err.Description
    On Error Resume Next
    If Not laHienTai Then
        If Not df Is Nothing Then df.Close
    End If
End Function

Private Sub XoaTrungDs(ByVal m As ModelReference, ByVal ee As ElementEnumerator, ByVal lvNguon As Long, _
                       ByVal tol As Double, ByRef nXoa As Long)
    Dim nhom As Object, el As Element, k As String, s As String, lv As Long
    Dim dS As Collection, cx As Double, cy As Double, i As Long, xoa As New Collection, trung As Boolean
    Dim p As Variant
    If ee Is Nothing Then Exit Sub
    Set nhom = CreateObject("Scripting.Dictionary")
    On Error Resume Next
    Do While ee.MoveNext
        Set el = ee.Current
        If el.Type = msdElementTypeText Or el.Type = msdElementTypeTextNode Then
            lv = DC_LevelSo(el)
            If lvNguon <= 0 Or lv = lvNguon Then
                s = Trim$(noiDung(el))
                If Len(s) > 0 Then
                    cx = (el.Range.Low.x + el.Range.High.x) / 2#
                    cy = (el.Range.Low.y + el.Range.High.y) / 2#
                    k = lv & "|" & s
                    If Not nhom.Exists(k) Then Set dS = New Collection: nhom.Add k, dS Else Set dS = nhom(k)
                    trung = False
                    For i = 1 To dS.Count
                        p = dS.Item(i)
                        If (p(0) - cx) ^ 2 + (p(1) - cy) ^ 2 <= tol * tol Then trung = True: Exit For
                    Next i
                    If trung Then
                        xoa.Add el
                    Else
                        dS.Add Array(cx, cy)
                    End If
                End If
            End If
        End If
        Err.Clear
    Loop
    For i = 1 To xoa.Count
        Err.Clear
        m.RemoveElement xoa.Item(i)
        If Err.Number = 0 Then nXoa = nXoa + 1
    Next i
    Err.Clear
End Sub

Attribute VB_Name = "modTaoThua"
Option Explicit

'============================================================
' modTaoThua (v2) - Tao thua tu ranh: ghep vung + ve tam + LUU CSDL
'============================================================

' Ten CSDL mac dinh theo ten file .dgn dang mo:  C:\DiaChinhVL\<ten>.txt
Public Function CsdlMacDinh() As String
    Dim nm As String, p As Long
    On Error Resume Next
    nm = ActiveDesignFile.Name          ' vd "dc01.dgn"
    On Error GoTo 0
    If Len(nm) = 0 Then nm = "csdl"
    p = InStrRev(nm, ".")
    If p > 0 Then nm = Left$(nm, p - 1) ' bo duoi .dgn
    ' SUA 22/10: CSDL de rieng thu muc C:\DiaChinhVL\CSDL\<ten>.txt
    '   (file cu C:\DiaChinhVL\<ten>.txt neu co -> chep sang, file cu giu nguyen)
    Dim cu As String, moi As String
    cu = "C:\DiaChinhVL\" & nm & ".txt"
    moi = "C:\DiaChinhVL\CSDL\" & nm & ".txt"
    CsdlMacDinh = moi
    On Error Resume Next
    If Len(Dir$("C:\DiaChinhVL", vbDirectory)) = 0 Then MkDir "C:\DiaChinhVL"
    If Len(Dir$("C:\DiaChinhVL\CSDL", vbDirectory)) = 0 Then MkDir "C:\DiaChinhVL\CSDL"
    If Len(Dir$("C:\DiaChinhVL\CSDL", vbDirectory)) = 0 Then CsdlMacDinh = cu: Exit Function
    If Len(Dir$(moi)) = 0 And Len(Dir$(cu)) > 0 Then FileCopy cu, moi
    Err.Clear
End Function

' SUA 22/10: so to ban do lay tu ten file .dgn dang mo (DC9.dgn -> 9, dc55 -> 55)
'   lay nhom chu so DAU TIEN trong ten; khong co -> ""
Public Function DC_ToTheoTenFile() As String
    Dim nm As String, i As Long, c As String, s As String
    On Error Resume Next
    nm = ActiveDesignFile.Name
    On Error GoTo 0
    i = InStrRev(nm, "."): If i > 0 Then nm = Left$(nm, i - 1)
    For i = 1 To Len(nm)
        c = Mid$(nm, i, 1)
        If c >= "0" And c <= "9" Then
            s = s & c
        ElseIf Len(s) > 0 Then
            Exit For
        End If
    Next i
    If Len(s) > 0 And Len(s) < 9 Then s = CStr(CLng(s))
    DC_ToTheoTenFile = s
End Function

Public Sub ChayTaoThua(ByVal levelsCSV As String, _
                       ByVal loaiDat As String, ByVal toBanDo As String, _
                       ByVal SoLe As Long, ByVal boNho As Double, _
                       ByVal snap As Double, ByVal levelTam As String, _
                       ByVal mauTam As Long, ByVal kt As Double, _
                       ByVal csdlPath As String, _
                       Optional ByVal mauCSV As String = "", _
                       Optional ByVal gapTol As Double = 0)

    If snap <= 0 Then snap = 0.05
    If kt <= 0 Then kt = 0.3

    Dim minX As Double, minY As Double, maxX As Double, maxY As Double
    Dim segs As Collection
    Set segs = LayDoanNhieuLevel(levelsCSV, snap, minX, minY, maxX, maxY, mauCSV)
    If segs.Count = 0 Then
        MsgBox "Khong doc duoc doan ranh nao tu cac level da chon.", vbExclamation, "Tao thua"
        Exit Sub
    End If

    ' Tu va ho ranh nho (neu bat)
    If gapTol > 0 Then Set segs = VaHoRanh(segs, snap, gapTol)

    Dim tia As Long, vungs As Collection
    Set vungs = GhepVung(segs, snap, tia)
    If vungs.Count = 0 Then MsgBox "Khong ghep duoc vung nao.", vbExclamation, "Tao thua": Exit Sub

    If Len(Trim$(levelTam)) > 0 Then
        On Error Resume Next
        ActiveSettings.Level = ActiveModelReference.Levels(Trim$(levelTam))
        On Error GoTo 0
    End If

    Dim i As Long, v As clsVung, dem As Long, tong As Double
    For i = 1 To vungs.Count
        Set v = vungs.Item(i)
        If boNho <= 0 Or v.dt >= boNho Then
            If Len(v.loaiDat) = 0 Then v.loaiDat = loaiDat
            If Len(v.SoTo) = 0 Then v.SoTo = toBanDo
            VeTamHong v.cx, v.cy, kt, mauTam
            dem = dem + 1
            tong = tong + v.dt
        End If
    Next i

    ' Luu CSDL
    Dim ok As Boolean, msgCSDL As String
    If Len(Trim$(csdlPath)) > 0 Then
        ok = LuuCSDL(vungs, csdlPath)
        msgCSDL = vbCrLf & IIf(ok, "Da luu CSDL: " & csdlPath, "KHONG luu duoc CSDL: " & csdlPath)
    End If

    Dim f As String
    If SoLe <= 0 Then f = "#,##0" Else f = "#,##0." & String$(SoLe, "0")
    MsgBox "So thua tao: " & dem & vbCrLf & _
           "Tong dien tich: " & Format$(tong, f) & " m2" & msgCSDL, _
           vbInformation, "Tao thua / tao CSDL"
End Sub

Attribute VB_Name = "modTaoVungDiem"
Option Explicit

'============================================================
' modTaoVungDiem - khoi dong che do "Tao vung theo diem bam".
'   Giu tham chieu cong cu o bien module de no song suot lenh.
'============================================================
Public gToolVung As clsTaoVungDiem

Public Sub DC_TaoVungTheoDiem(ByVal levelsCSV As String, ByVal loaiDat As String, _
        ByVal toBanDo As String, ByVal snap As Double, ByVal levelTam As String, _
        ByVal mauTam As Long, ByVal kt As Double, ByVal csdlPath As String, _
        ByVal mauCSV As String, ByVal gapTol As Double)

    If snap <= 0 Then snap = 0.05
    If kt <= 0 Then kt = 0.3

    Dim minX As Double, minY As Double, maxX As Double, maxY As Double
    Dim segs As Collection
    Set segs = LayDoanNhieuLevel(levelsCSV, snap, minX, minY, maxX, maxY, mauCSV)
    If segs.Count = 0 Then MsgBox "Khong doc duoc ranh tu cac level da chon.", vbExclamation, "Tao vung theo diem": Exit Sub
    If gapTol > 0 Then Set segs = VaHoRanh(segs, snap, gapTol)

    Dim tia As Long, vungs As Collection
    Set vungs = GhepVung(segs, snap, tia)
    If vungs.Count = 0 Then MsgBox "Khong ghep duoc vung nao.", vbExclamation, "Tao vung theo diem": Exit Sub

    If Len(Trim$(levelTam)) > 0 Then
        On Error Resume Next
        ActiveSettings.Level = ActiveModelReference.Levels(Trim$(levelTam))
        On Error GoTo 0
    End If

    Set gToolVung = New clsTaoVungDiem
    Set gToolVung.vungs = vungs
    gToolVung.loaiDat = loaiDat
    gToolVung.toBanDo = toBanDo
    gToolVung.kt = kt
    gToolVung.mauTam = mauTam
    gToolVung.csdlPath = csdlPath

    CommandState.StartPrimitive gToolVung
End Sub

Attribute VB_Name = "modTest"
Option Explicit

'============================================================
' modTest - kiem thu modHinhHoc
' Chay: dat con tro trong 1 Sub roi nhan F5
'       (hoac Utilities > Macro > Macros... trong MicroStation)
'============================================================

'--- Thu 1: thua vuong 100 x 100 -> 1 vung, Dt = 10000, tam (50,50) ---
Public Sub Test_ThuaVuong()
    Dim segs As New Collection
    segs.Add NewSeg(0#, 0#, 100#, 0#)
    segs.Add NewSeg(100#, 0#, 100#, 100#)
    segs.Add NewSeg(100#, 100#, 0#, 100#)
    segs.Add NewSeg(0#, 100#, 0#, 0#)

    Dim soTia As Long
    Dim vungs As Collection
    Set vungs = GhepVung(segs, 0.001, soTia)

    Dim s As String, i As Long, v As clsVung
    s = "So vung tim duoc: " & vungs.Count & vbCrLf
    s = s & "So canh cut (soTia): " & soTia & vbCrLf & vbCrLf
    For i = 1 To vungs.Count
        Set v = vungs.Item(i)
        s = s & "Vung " & i & ":" & vbCrLf
        s = s & "  Dien tich = " & Format$(v.dt, "0.0") & vbCrLf
        s = s & "  Tam       = (" & Format$(v.cx, "0.0") & ", " & Format$(v.cy, "0.0") & ")" & vbCrLf
        s = s & "  So dao    = " & v.NDao & vbCrLf
    Next i
    MsgBox s, vbInformation, "Test_ThuaVuong"
    ' Ky vong: 1 vung, Dt = 10000.0, tam (50.0, 50.0), 0 dao
End Sub


'--- Thu 2: thua vuong 100x100 co lo dao 40x40 o giua ---
'    Ky vong: 2 vung -> mot vung Dt=8400 co 1 dao, mot vung Dt=1600 khong dao
Public Sub Test_ThuaCoDao()
    Dim segs As New Collection
    ' vien ngoai
    segs.Add NewSeg(0#, 0#, 100#, 0#)
    segs.Add NewSeg(100#, 0#, 100#, 100#)
    segs.Add NewSeg(100#, 100#, 0#, 100#)
    segs.Add NewSeg(0#, 100#, 0#, 0#)
    ' lo dao ben trong (30..70)
    segs.Add NewSeg(30#, 30#, 70#, 30#)
    segs.Add NewSeg(70#, 30#, 70#, 70#)
    segs.Add NewSeg(70#, 70#, 30#, 70#)
    segs.Add NewSeg(30#, 70#, 30#, 30#)

    Dim soTia As Long
    Dim vungs As Collection
    Set vungs = GhepVung(segs, 0.001, soTia)

    Dim s As String, i As Long, v As clsVung
    s = "So vung tim duoc: " & vungs.Count & vbCrLf & vbCrLf
    For i = 1 To vungs.Count
        Set v = vungs.Item(i)
        s = s & "Vung " & i & ": Dt = " & Format$(v.dt, "0.0") _
              & " ; so dao = " & v.NDao _
              & " ; tam (" & Format$(v.cx, "0.0") & "," & Format$(v.cy, "0.0") & ")" & vbCrLf
    Next i
    MsgBox s, vbInformation, "Test_ThuaCoDao"
    ' Ky vong: vung ngoai Dt=8400 co 1 dao ; vung trong Dt=1600 khong dao
End Sub


'--- Thu 3: tim diem ho (bo bot 1 canh -> ho 2 dau) ---
Public Sub Test_TimDiemHo()
    Dim segs As New Collection
    segs.Add NewSeg(0#, 0#, 100#, 0#)
    segs.Add NewSeg(100#, 0#, 100#, 100#)
    segs.Add NewSeg(100#, 100#, 0#, 100#)
    ' KHONG dong canh cuoi -> ho tai (0,0) va (0,100)

    Dim ho As Collection
    Set ho = TimDiemHo(segs, 0.001)

    Dim s As String, i As Long, p() As Double
    s = "So diem ho: " & ho.Count & vbCrLf
    For i = 1 To ho.Count
        p = ho.Item(i)
        s = s & "  (" & Format$(p(0), "0.0") & ", " & Format$(p(1), "0.0") & ")" & vbCrLf
    Next i
    MsgBox s, vbInformation, "Test_TimDiemHo"
    ' Ky vong: 2 diem ho -> (0,0) va (0,100)
End Sub

Attribute VB_Name = "modThuaKe"
'============================================================
' modThuaKe - GHI SO THUA LIEN KE quanh thua trong so do trich luc / tach / hop
'   Lay tu CSDL (mac dinh theo ten ban ve). So thua trong -> "0".
'   Thua khac to: "538 (To 46)". Chi ghi khi nhan nam trong o so do.
'   ini: TL_THUAKE = 0 de tat.
'============================================================
Option Explicit

Private mDs As Collection, mPath As String, mTg As Date
Private Const tol As Double = 0.05

' v: thua chinh ; (ox,oy) = vi tri ve cua diem (gx,gy) ; kp = ty le so do
' h: co chu ; (bx,by,bw,bh) = tam + kich thuoc o so do (toa do ve) ; toBD = so to cua thua chinh
Public Sub TK_VeThuaKe(ByVal v As clsVung, ByVal ox As Double, ByVal oy As Double, _
                       ByVal gx As Double, ByVal gy As Double, ByVal kp As Double, ByVal h As Double, _
                       ByVal bx As Double, ByVal by As Double, ByVal bw As Double, ByVal bh As Double, _
                       ByVal toBD As String)
    Dim dS As Collection, w As clsVung, i As Long, rg() As Double, rw() As Double
    Dim px As Double, py As Double, x As Double, y As Double, s As String
    On Error GoTo Thoi
    If DC_DocCauHinh("TL_THUAKE", "1") = "0" Then Exit Sub
    If v Is Nothing Then Exit Sub
    If Not v.HasRing Then Exit Sub
    If h <= 0 Or kp <= 0 Then Exit Sub
    Set dS = DsThua()
    If dS Is Nothing Then Exit Sub
    rg = v.ring
    Dim x1 As Double, y1 As Double, x2 As Double, y2 As Double
    BaoRing rg, x1, y1, x2, y2
    toBD = Trim$(toBD)
    For i = 1 To dS.Count
        Set w = dS.Item(i)
        If w.HasRing Then
            rw = w.ring
            If Not NgoaiHop(rw, x1 - tol, y1 - tol, x2 + tol, y2 + tol) Then
                If Not DiemTrongPolygon(rg, w.cx, w.cy) Then          ' bo chinh no / thua con ben trong
                    If ViTriNhan(rg, rw, v, w, h / kp, px, py) Then
                        x = ox + (px - gx) * kp: y = oy + (py - gy) * kp
                        If Abs(x - bx) < bw / 2# - h * 1.5 And Abs(y - by) < bh / 2# - h Then
                            s = Trim$(w.soThua)
                            If Len(s) = 0 Then s = "0"
                            If Len(Trim$(w.SoTo)) > 0 And Len(toBD) > 0 And Trim$(w.SoTo) <> toBD Then
                                s = s & " (T" & ChrW(7901) & " " & Trim$(w.SoTo) & ")"
                            End If
                            VeText x, y, s, h, -1
                        End If
                    End If
                End If
            End If
        End If
    Next i
Thoi:
End Sub

' CSDL theo ban ve dang mo (nho dem, doc lai khi file doi)
Private Function DsThua() As Collection
    Dim p As String, tg As Date
    On Error Resume Next
    p = CsdlMacDinh()
    If Len(Dir$(p)) = 0 Then Exit Function
    tg = FileDateTime(p)
    If Not mDs Is Nothing And p = mPath And tg = mTg Then Set DsThua = mDs: Exit Function
    Set mDs = MoCSDL(p): mPath = p: mTg = tg
    Set DsThua = mDs
End Function

Private Function NgoaiHop(rw() As Double, ByVal x1 As Double, ByVal y1 As Double, ByVal x2 As Double, ByVal y2 As Double) As Boolean
    Dim a1 As Double, b1 As Double, a2 As Double, b2 As Double
    BaoRing rw, a1, b1, a2, b2
    NgoaiHop = (a2 < x1 Or a1 > x2 Or b2 < y1 Or b1 > y2)
End Function

' Tim cac diem chung tren ranh 2 thua ; >= 2 diem = lien ke (chung canh).
' Vi tri nhan: trung diem doan chung, day vao trong thua w.
Private Function ViTriNhan(rg() As Double, rw() As Double, ByVal v As clsVung, ByVal w As clsVung, _
                           ByVal hThat As Double, ByRef px As Double, ByRef py As Double) As Boolean
    Dim xs() As Double, ys() As Double, n As Long, i As Long, j As Long
    Dim m As Long, mw As Long, dMax As Double, d As Double, ia As Long, ib As Long
    m = UBound(rg, 1): mw = UBound(rw, 1)
    ReDim xs(1 To m + mw + 2): ReDim ys(1 To m + mw + 2)
    For i = 0 To mw - 1
        If TrenRanh(rg, rw(i, 0), rw(i, 1)) Then n = n + 1: xs(n) = rw(i, 0): ys(n) = rw(i, 1)
    Next i
    For i = 0 To m - 1
        If TrenRanh(rw, rg(i, 0), rg(i, 1)) Then n = n + 1: xs(n) = rg(i, 0): ys(n) = rg(i, 1)
    Next i
    If n < 2 Then Exit Function
    ia = 1: ib = 1
    For i = 1 To n - 1
        For j = i + 1 To n
            d = (xs(i) - xs(j)) ^ 2 + (ys(i) - ys(j)) ^ 2
            If d > dMax Then dMax = d: ia = i: ib = j
        Next j
    Next i
    If dMax < tol * tol Then Exit Function
    Dim mx As Double, my As Double, ux As Double, uy As Double, L As Double, k As Double, t As Variant
    mx = (xs(ia) + xs(ib)) / 2#: my = (ys(ia) + ys(ib)) / 2#
    ' phap tuyen cua doan chung, chon phia nam trong w
    ux = -(ys(ib) - ys(ia)): uy = xs(ib) - xs(ia)
    L = Sqr(ux * ux + uy * uy): ux = ux / L: uy = uy / L
    For Each t In Array(2#, 3#, 4.5, 6.5, 9#)
        k = t * hThat
        If DiemTrongPolygon(rw, mx + ux * k, my + uy * k) Then px = mx + ux * k: py = my + uy * k: ViTriNhan = True: Exit Function
        If DiemTrongPolygon(rw, mx - ux * k, my - uy * k) Then px = mx - ux * k: py = my - uy * k: ViTriNhan = True: Exit Function
    Next t
    ' khong dat duoc gan ranh -> dung tam thua lien ke
    px = w.cx: py = w.cy: ViTriNhan = True
End Function

' Diem (x,y) nam tren ranh ngoai rg (sai so TOL)
Private Function TrenRanh(rg() As Double, ByVal x As Double, ByVal y As Double) As Boolean
    Dim i As Long, m As Long, ax As Double, ay As Double, dx As Double, dy As Double, L2 As Double, t As Double, qx As Double, qy As Double
    m = UBound(rg, 1)
    For i = 0 To m - 1
        ax = rg(i, 0): ay = rg(i, 1): dx = rg(i + 1, 0) - ax: dy = rg(i + 1, 1) - ay
        L2 = dx * dx + dy * dy
        If L2 > 0 Then
            t = ((x - ax) * dx + (y - ay) * dy) / L2
            If t >= -0.001 And t <= 1.001 Then
                qx = ax + t * dx - x: qy = ay + t * dy - y
                If qx * qx + qy * qy <= tol * tol Then TrenRanh = True: Exit Function
            End If
        End If
    Next i
End Function

Attribute VB_Name = "modThuocTinh"
Option Explicit

'============================================================
' modThuocTinh - Doc so thua (Text + TextNode) & gan vao thua
'   Text     : el.Text, el.Origin
'   TextNode : el.Origin ; noi dung = dong dau (GetSubElements)
'============================================================


'============================================================
' Doc 1 phan tu text -> (x, y, chuoi). Ho tro Text va TextNode.
'============================================================
Private Function DocMotText(ByVal el As Element, ByRef x As Double, _
                            ByRef y As Double, ByRef s As String) As Boolean
    DocMotText = False
    s = ""
    Dim o As Point3d

    If el.Type = msdElementTypeText Then
        Dim oT As TextElement
        Set oT = el
        o = oT.Origin
        x = o.x: y = o.y
        s = Trim$(oT.Text)
        DocMotText = True

    ElseIf el.Type = msdElementTypeTextNode Then
        Dim oNode As TextNodeElement
        Set oNode = el
        o = oNode.Origin
        x = o.x: y = o.y
        Dim subs As ElementEnumerator
        Set subs = oNode.GetSubElements
        Do While subs.MoveNext
            If subs.Current.Type = msdElementTypeText Then
                s = Trim$(subs.Current.AsTextElement.Text)
                If Len(s) > 0 Then Exit Do
            End If
        Loop
        DocMotText = True
    End If
End Function


'============================================================
' Tim thua chua diem (x,y): ring chua diem & khong trong lo dao;
' nhieu thua long nhau -> chon thua dien tich NHO NHAT.
'============================================================
Public Function TimThuaChua(ByVal vungs As Collection, _
                            ByVal x As Double, ByVal y As Double) As clsVung
    Dim i As Long, k As Long, v As clsVung
    Dim r() As Double, dr() As Double
    Dim trongDao As Boolean
    Dim best As clsVung, bestDt As Double
    Set best = Nothing
    bestDt = 1E+300

    For i = 1 To vungs.Count
        Set v = vungs.Item(i)
        If v.HasRing Then
            r = v.ring
            If DiemTrongPolygon(r, x, y) Then
                trongDao = False
                For k = 1 To v.dao.Count
                    dr = v.dao.Item(k)
                    If DiemTrongPolygon(dr, x, y) Then trongDao = True: Exit For
                Next k
                If Not trongDao And v.dt < bestDt Then
                    Set best = v
                    bestDt = v.dt
                End If
            End If
        End If
    Next i
    Set TimThuaChua = best
End Function


Private Function TenLevelActive() As String
    On Error Resume Next
    TenLevelActive = ActiveSettings.Level.Name
    On Error GoTo 0
End Function

Private Function CoChuUocLuong(ByVal minX As Double, ByVal minY As Double, _
                               ByVal maxX As Double, ByVal maxY As Double) As Double
    Dim s As Double
    s = ((maxX - minX) + (maxY - minY)) / 2# / 1500#
    If s <= 0# Then s = 1#
    CoChuUocLuong = s
End Function


'============================================================
' LENH CHAY DUOC: GAN SO THUA (Text + TextNode) + chan doan
'============================================================
Public Sub DC_GanSoThua()
    Dim lvRanh As String, lvSo As String, snapStr As String, snap As Double

    lvRanh = InputBox("TEN level chua RANH thua:", "Gan so thua", TenLevelActive())
    lvSo = InputBox("TEN level chua SO THUA (Text/TextNode):" & vbCrLf & _
                    "(De trong = quet tat ca)", "Gan so thua", "")
    snapStr = InputBox("Dung sai noi diem (snap):", "Gan so thua", "0.05")
    If snapStr = "" Then Exit Sub
    snap = val(snapStr)
    If snap <= 0 Then snap = 0.05

    ' 1) Doc ranh + ghep vung
    Dim minX As Double, minY As Double, maxX As Double, maxY As Double
    Dim segs As Collection
    Set segs = LayCacDoan(snap, lvRanh, minX, minY, maxX, maxY)
    If segs.Count = 0 Then
        MsgBox "Khong doc duoc doan ranh nao.", vbExclamation, "Gan so thua"
        Exit Sub
    End If
    Dim soTia As Long, vungs As Collection
    Set vungs = GhepVung(segs, snap, soTia)
    If vungs.Count = 0 Then
        MsgBox "Khong ghep duoc vung nao.", vbExclamation, "Gan so thua"
        Exit Sub
    End If

    ' 2) Quet Text + TextNode
    Dim esc As ElementScanCriteria
    Set esc = New ElementScanCriteria
    esc.ExcludeAllTypes
    esc.IncludeType msdElementTypeText
    esc.IncludeType msdElementTypeTextNode
    If Len(Trim$(lvSo)) > 0 Then
        Dim lv As Level
        On Error Resume Next
        Set lv = ActiveModelReference.Levels(lvSo)
        On Error GoTo 0
        If Not lv Is Nothing Then esc.ExcludeAllLevels: esc.IncludeLevel lv
    End If

    Dim ee As ElementEnumerator
    Set ee = ActiveModelReference.Scan(esc)

    Dim nText As Long, nNode As Long, demGan As Long
    Dim tMinX As Double, tMinY As Double, tMaxX As Double, tMaxY As Double
    Dim firstT As Boolean: firstT = True
    Dim x As Double, y As Double, s As String, v As clsVung
    Dim el As Element

    Do While ee.MoveNext
        Set el = ee.Current
        If el.Type = msdElementTypeText Then nText = nText + 1
        If el.Type = msdElementTypeTextNode Then nNode = nNode + 1
        If DocMotText(el, x, y, s) Then
            If firstT Then
                tMinX = x: tMaxX = x: tMinY = y: tMaxY = y: firstT = False
            Else
                If x < tMinX Then tMinX = x
                If x > tMaxX Then tMaxX = x
                If y < tMinY Then tMinY = y
                If y > tMaxY Then tMaxY = y
            End If
            If Len(s) > 0 Then
                Set v = TimThuaChua(vungs, x, y)
                If Not v Is Nothing Then
                    If Len(v.soThua) = 0 Then v.soThua = s: demGan = demGan + 1
                End If
            End If
        End If
    Loop

    ' 3) Chan doan
    Dim chan As String
    chan = "So thua (vung): " & vungs.Count & vbCrLf & _
           "Text roi: " & nText & " ; TextNode: " & nNode & vbCrLf & _
           "Da gan vao thua: " & demGan & vbCrLf & vbCrLf & _
           "Khoang toa do THUA:" & vbCrLf & _
           "  X: " & Format$(minX, "0") & " .. " & Format$(maxX, "0") & vbCrLf & _
           "  Y: " & Format$(minY, "0") & " .. " & Format$(maxY, "0") & vbCrLf & _
           "Khoang toa do TEXT:" & vbCrLf & _
           "  X: " & Format$(tMinX, "0") & " .. " & Format$(tMaxX, "0") & vbCrLf & _
           "  Y: " & Format$(tMinY, "0") & " .. " & Format$(tMaxY, "0") & vbCrLf & vbCrLf & _
           "Ve nhan phan so bay gio?"

    If MsgBox(chan, vbInformation + vbYesNo, "Gan so thua - chan doan") <> vbYes Then Exit Sub

    ' 4) Ve nhan
    Dim caoStr As String, cao As Double
    cao = CoChuUocLuong(minX, minY, maxX, maxY)
    caoStr = InputBox("Co chu nhan (chieu cao):", "Gan so thua", Format$(cao, "0.###"))
    If caoStr <> "" Then cao = val(caoStr)
    If cao <= 0 Then cao = 1

    Dim i As Long, dtStr As String
    For i = 1 To vungs.Count
        Set v = vungs.Item(i)
        dtStr = Format$(Round(v.dt, 1), "0.0")
        If Len(v.soThua) > 0 Then
            VeNhanPhanSo v.cx, v.cy, v.soThua, dtStr, cao, 0
        Else
            VeText v.cx, v.cy, dtStr, cao, 2
        End If
    Next i
End Sub

Attribute VB_Name = "modTienIch"
'============================================================
' modTienIch - Menu Tien ich (lop, chon/xoa theo thuoc tinh, chieu dai
'   canh, doi font TCVN3 -> Unicode). Moi lenh sua ban ve deu dat "mark"
'   truoc -> key-in "undo mark" de tra lai.
'============================================================
Option Explicit

Private Function TIEU_DE() As String
    TIEU_DE = "Ti" & ChrW(7879) & "n " & ChrW(237) & "ch"
End Function

'============================================================
' LOP (LEVEL) - bat/tat trong moi view dang mo
'============================================================
Public Sub DC_BatTatCaLop()
    Dim vw As View, vi As Long, lv As Level
    On Error Resume Next
    For vi = 1 To 8
        Set vw = Nothing
        Set vw = ActiveDesignFile.Views(vi)
        If Not vw Is Nothing Then
            If vw.IsOpen Then
                For Each lv In ActiveDesignFile.Levels
                    lv.IsDisplayedInView(vw) = True
                Next lv
            End If
        End If
    Next vi
    For Each lv In ActiveDesignFile.Levels
        lv.IsDisplayed = True
    Next lv
    ActiveDesignFile.Levels.Rewrite
    On Error GoTo 0
    RedrawAllViews
End Sub

' Tat het (tru lop dang lam viec - MicroStation khong cho tat lop active)
Public Sub DC_TatTatCaLop()
    TatTheoDieuKien Nothing, False
End Sub

' Chi hien cac lop cua doi tuong dang chon (tat cac lop khac)
Public Sub DC_BatLopDoiTuongChon()
    Dim dS As Object
    Set dS = LopDangChon()
    If dS Is Nothing Then Exit Sub
    BatDanhSach dS
    TatTheoDieuKien dS, False
End Sub

' Tat cac lop cua doi tuong dang chon
Public Sub DC_TatLopDoiTuongChon()
    Dim dS As Object
    Set dS = LopDangChon()
    If dS Is Nothing Then Exit Sub
    TatTheoDieuKien dS, True
End Sub

' tatTrongDs = True : tat cac lop CO trong ds ; False : tat cac lop KHONG co trong ds
' (ds = Nothing -> tat het)
Private Sub TatTheoDieuKien(ByVal dS As Object, ByVal tatTrongDs As Boolean)
    Dim vw As View, vi As Long, lv As Level, act As Long, CoTrong As Boolean, tat As Boolean
    On Error Resume Next
    act = -1
    act = ActiveSettings.Level.Number
    ' lop active nam trong nhom bi tat -> chuyen lop active sang lop duoc giu
    If Not dS Is Nothing Then
        CoTrong = dS.Exists(CStr(act))
        If CoTrong = tatTrongDs Then
            For Each lv In ActiveDesignFile.Levels
                If dS.Exists(CStr(lv.Number)) <> tatTrongDs Then Set ActiveSettings.Level = lv: act = lv.Number: Exit For
            Next lv
        End If
    End If
    For vi = 1 To 8
        Set vw = Nothing
        Set vw = ActiveDesignFile.Views(vi)
        If Not vw Is Nothing Then
            If vw.IsOpen Then
                For Each lv In ActiveDesignFile.Levels
                    If dS Is Nothing Then
                        tat = True
                    Else
                        tat = (dS.Exists(CStr(lv.Number)) = tatTrongDs)
                    End If
                    If tat And lv.Number <> act Then lv.IsDisplayedInView(vw) = False
                Next lv
            End If
        End If
    Next vi
    On Error GoTo 0
    RedrawAllViews
End Sub

Private Sub BatDanhSach(ByVal dS As Object)
    Dim vw As View, vi As Long, lv As Level
    On Error Resume Next
    For vi = 1 To 8
        Set vw = Nothing
        Set vw = ActiveDesignFile.Views(vi)
        If Not vw Is Nothing Then
            If vw.IsOpen Then
                For Each lv In ActiveDesignFile.Levels
                    If dS.Exists(CStr(lv.Number)) Then lv.IsDisplayedInView(vw) = True
                Next lv
            End If
        End If
    Next vi
End Sub

' So lop cua cac doi tuong dang chon (Nothing + bao loi neu chua chon)
Private Function LopDangChon() As Object
    Dim dS As Object, ee As ElementEnumerator
    Set dS = CreateObject("Scripting.Dictionary")
    On Error Resume Next
    Set ee = ActiveModelReference.GetSelectedElements
    On Error GoTo 0
    If Not ee Is Nothing Then
        Do While ee.MoveNext
            dS(CStr(DC_LevelSo(ee.Current))) = True
        Loop
    End If
    If dS.Count = 0 Then
        DC_ThongBao "H" & ChrW(227) & "y ch" & ChrW(7885) & "n (m" & ChrW(361) & "i t" & ChrW(234) & "n Element Selection) " & ChrW(237) & "t nh" & ChrW(7845) & "t 1 " & ChrW(273) & ChrW(7889) & "i t" & ChrW(432) & ChrW(7907) & "ng tr" & ChrW(432) & ChrW(7899) & "c.", TIEU_DE, vbExclamation
        Exit Function
    End If
    Set LopDangChon = dS
End Function

'============================================================
' CHON / XOA THEO THUOC TINH hoac THEO LOP cua doi tuong dang chon
'   theoLop = False : cung loai + lop + mau + kieu net + do day
'   theoLop = True  : cung lop
'============================================================
Public Sub DC_ChonTheoThuocTinh()
    ChonXoa False, False
End Sub
Public Sub DC_XoaTheoThuocTinh()
    ChonXoa False, True
End Sub
Public Sub DC_ChonTheoLop()
    ChonXoa True, False
End Sub
Public Sub DC_XoaLopDoiTuongChon()
    ChonXoa True, True
End Sub

Private Sub ChonXoa(ByVal theoLop As Boolean, ByVal xoa As Boolean)
    Dim mau As Object, ee As ElementEnumerator, el As Element, k As String
    Set mau = CreateObject("Scripting.Dictionary")
    On Error Resume Next
    Set ee = ActiveModelReference.GetSelectedElements
    On Error GoTo 0
    If Not ee Is Nothing Then
        Do While ee.MoveNext
            mau(KhoaThuocTinh(ee.Current, theoLop)) = True
        Loop
    End If
    If mau.Count = 0 Then
        DC_ThongBao "H" & ChrW(227) & "y ch" & ChrW(7885) & "n (m" & ChrW(361) & "i t" & ChrW(234) & "n Element Selection) " & ChrW(237) & "t nh" & ChrW(7845) & "t 1 " & ChrW(273) & ChrW(7889) & "i t" & ChrW(432) & ChrW(7907) & "ng m" & ChrW(7851) & "u tr" & ChrW(432) & ChrW(7899) & "c.", TIEU_DE, vbExclamation
        Exit Sub
    End If

    Dim esc As New ElementScanCriteria, dS() As Element, n As Long, i As Long
    esc.ExcludeNonGraphical
    ReDim dS(1 To 256)
    Set ee = ActiveModelReference.Scan(esc)
    Do While ee.MoveNext
        Set el = ee.Current
        If mau.Exists(KhoaThuocTinh(el, theoLop)) Then
            n = n + 1
            If n > UBound(dS) Then ReDim Preserve dS(1 To n * 2)
            Set dS(n) = el
        End If
    Loop
    If n = 0 Then Exit Sub

    If xoa Then
        If DC_ThongBao("X" & ChrW(243) & "a " & n & " " & ChrW(273) & ChrW(7889) & "i t" & ChrW(432) & ChrW(7907) & "ng " & IIf(theoLop, "tr" & ChrW(234) & "n c" & ChrW(249) & "ng l" & ChrW(7899) & "p", "c" & ChrW(249) & "ng thu" & ChrW(7897) & "c t" & ChrW(237) & "nh") & _
                       " v" & ChrW(7899) & "i " & ChrW(273) & ChrW(7889) & "i t" & ChrW(432) & ChrW(7907) & "ng " & ChrW(273) & "ang ch" & ChrW(7885) & "n?" & vbCrLf & "(Sai: key-in undo mark)", TIEU_DE, vbYesNo Or vbQuestion) <> vbYes Then Exit Sub
        On Error Resume Next
        CadInputQueue.SendKeyin "mark"
        ActiveModelReference.UnselectAllElements
        For i = 1 To n
            ActiveModelReference.RemoveElement dS(i)
        Next i
        On Error GoTo 0
        RedrawAllViews
        ShowStatus "Da xoa " & n & " doi tuong"
    Else
        On Error Resume Next
        ActiveModelReference.UnselectAllElements
        For i = 1 To n
            ActiveModelReference.SelectElement dS(i)
        Next i
        On Error GoTo 0
        ShowStatus "Da chon " & n & " doi tuong"
    End If
End Sub

Private Function KhoaThuocTinh(ByVal el As Element, ByVal theoLop As Boolean) As String
    Dim s As String
    s = CStr(DC_LevelSo(el))
    If theoLop Then KhoaThuocTinh = s: Exit Function
    On Error Resume Next
    s = s & "|" & el.Type & "|" & el.color & "|" & el.LineWeight
    s = s & "|" & el.LineStyle.Name
    KhoaThuocTinh = s
End Function

'============================================================
' GHI CHU CHIEU DAI CANH: doi tuong dang chon (line, linestring, shape,
' complex) -> ghi chieu dai tung canh, chu xoay theo canh, dat phia ngoai.
'============================================================
Public Sub DC_GhiChieuDaiCanh()
    Dim ee As ElementEnumerator, el As Element, n As Long
    On Error Resume Next
    Set ee = ActiveModelReference.GetSelectedElements
    On Error GoTo 0
    Dim dS As New Collection
    If Not ee Is Nothing Then
        Do While ee.MoveNext
            dS.Add ee.Current
        Loop
    End If
    If dS.Count = 0 Then
        DC_ThongBao "H" & ChrW(227) & "y ch" & ChrW(7885) & "n c" & ChrW(225) & "c c" & ChrW(7841) & "nh / ranh th" & ChrW(7917) & "a (line, linestring, shape) r" & ChrW(7891) & "i b" & ChrW(7845) & "m l" & ChrW(7841) & "i.", TIEU_DE, vbExclamation
        Exit Sub
    End If
    Dim s As String, cao As Double, SoLe As Long
    s = InputBox("Co chu (don vi ban ve, vd 0.5):", "Ghi chieu dai canh", DC_DocCauHinh("CD_CAO", "0.5"))
    If Len(Trim$(s)) = 0 Then Exit Sub
    cao = val(Replace(s, ",", ".")): If cao <= 0 Then Exit Sub
    s = InputBox("So le (vd 2):", "Ghi chieu dai canh", DC_DocCauHinh("CD_SOLE", "2"))
    If Len(Trim$(s)) = 0 Then Exit Sub
    SoLe = CLng(val(s))
    DC_GhiCauHinh "CD_CAO", CStr(cao): DC_GhiCauHinh "CD_SOLE", CStr(SoLe)

    On Error Resume Next
    CadInputQueue.SendKeyin "mark"
    On Error GoTo 0
    DC_DatFontViet
    Dim i As Long
    For i = 1 To dS.Count
        n = n + GhiMotPhanTu(dS.Item(i), cao, SoLe)
    Next i
    RedrawAllViews
    ShowStatus "Da ghi " & n & " chieu dai canh"
End Sub

Private Function GhiMotPhanTu(ByVal el As Element, ByVal cao As Double, ByVal SoLe As Long) As Long
    Dim subs As ElementEnumerator, pts() As Point3d, i As Long, m As Long, a As Double, chieu As Double
    On Error Resume Next
    If el.IsComplexElement And Not el.IsVertexList Then
        Set subs = el.AsComplexElement.GetSubElements
        Do While subs.MoveNext
            GhiMotPhanTu = GhiMotPhanTu + GhiMotPhanTu(subs.Current, cao, SoLe)
        Loop
        Exit Function
    End If
    If Not el.IsVertexList Then Exit Function
    Err.Clear
    pts = el.AsVertexList.GetVertices
    If Err.Number <> 0 Then Exit Function
    On Error GoTo 0
    m = UBound(pts) - LBound(pts)
    ' chieu vong: CCW (a > 0) -> phia ngoai la ben PHAI canh
    For i = LBound(pts) To UBound(pts) - 1
        a = a + pts(i).x * pts(i + 1).y - pts(i + 1).x * pts(i).y
    Next i
    If a >= 0 Then chieu = 1# Else chieu = -1#
    For i = LBound(pts) To UBound(pts) - 1
        If GhiCanh(pts(i).x, pts(i).y, pts(i + 1).x, pts(i + 1).y, cao, SoLe, chieu) Then GhiMotPhanTu = GhiMotPhanTu + 1
    Next i
End Function

Private Function GhiCanh(ByVal ax As Double, ByVal ay As Double, ByVal bx As Double, ByVal by As Double, _
                         ByVal h As Double, ByVal SoLe As Long, ByVal chieu As Double) As Boolean
    Dim dx As Double, dy As Double, L As Double, ang As Double, mx As Double, my As Double, f As String
    dx = bx - ax: dy = by - ay
    L = Sqr(dx * dx + dy * dy)
    If L < h * 0.5 Then Exit Function
    ang = Atan2(dy, dx)
    If ang > 1.5708 Then ang = ang - 3.14159265358979
    If ang <= -1.5708 Then ang = ang + 3.14159265358979
    mx = (ax + bx) / 2# + dy / L * h * 0.8 * chieu
    my = (ay + by) / 2# - dx / L * h * 0.8 * chieu
    If SoLe <= 0 Then f = "0" Else f = "0." & String$(SoLe, "0")
    On Error Resume Next
    ActiveSettings.TextStyle.Height = h
    ActiveSettings.TextStyle.Width = h * 0.774
    ActiveSettings.TextStyle.Justification = msdTextJustificationCenterCenter
    Dim oT As TextElement
    Set oT = CreateTextElement1(Nothing, Replace(Format$(L, f), ".", ","), Point3dFromXYZ(mx, my, 0#), _
                                Matrix3dFromAxisAndRotationAngle(2, ang))
    If Not oT Is Nothing Then
        oT.LineWeight = 0
        ActiveModelReference.AddElement oT
        GhiCanh = True
    End If
End Function

'============================================================
' DOI FONT TCVN3 (.VnTime...) -> UNICODE (Times New Roman)
'   Co chon -> chi doi chu dang chon ; khong chon -> hoi doi ca ban ve.
'============================================================
Public Sub DC_DoiFontTcvn3()
    Dim ee As ElementEnumerator, dS As New Collection, el As Element
    On Error Resume Next
    Set ee = ActiveModelReference.GetSelectedElements
    On Error GoTo 0
    If Not ee Is Nothing Then
        Do While ee.MoveNext
            dS.Add ee.Current
        Loop
    End If
    If dS.Count = 0 Then
        If DC_ThongBao("Ch" & ChrW(432) & "a ch" & ChrW(7885) & "n ch" & ChrW(7919) & " n" & ChrW(224) & "o. " & ChrW(272) & ChrW(7893) & "i T" & ChrW(7844) & "T C" & ChrW(7842) & " ch" & ChrW(7919) & " font TCVN3 (.VnTime...) trong b" & ChrW(7843) & "n v" & ChrW(7869) & " sang Unicode (Times New Roman)?", _
                       TIEU_DE, vbYesNo Or vbQuestion) <> vbYes Then Exit Sub
        Dim esc As New ElementScanCriteria
        esc.ExcludeAllTypes
        esc.IncludeType msdElementTypeText
        esc.IncludeType msdElementTypeTextNode
        Set ee = ActiveModelReference.Scan(esc)
        Do While ee.MoveNext
            dS.Add ee.Current
        Loop
    End If

    Dim fnt As Object
    Set fnt = TimFontTen(DC_FONT_VIET)
    If fnt Is Nothing Then Set fnt = TimFontTen("Arial")
    If fnt Is Nothing Then DC_ThongBao "Kh" & ChrW(244) & "ng t" & ChrW(236) & "m th" & ChrW(7845) & "y font " & DC_FONT_VIET & " trong MicroStation.", TIEU_DE, vbExclamation: Exit Sub

    On Error Resume Next
    CadInputQueue.SendKeyin "mark"
    On Error GoTo 0
    Dim i As Long, n As Long
    For i = 1 To dS.Count
        n = n + DoiMotChu(dS.Item(i), fnt)
    Next i
    RedrawAllViews
    DC_ThongBao ChrW(272) & ChrW(227) & " " & ChrW(273) & ChrW(7893) & "i " & n & " ch" & ChrW(7919) & " sang Unicode (" & fnt.Name & ")." & vbCrLf & "(Sai: key-in undo mark)", TIEU_DE
End Sub

Private Function DoiMotChu(ByVal el As Element, ByVal fnt As Object) As Long
    Dim subs As ElementEnumerator, oT As TextElement, fn As String, s As String, ts As TextStyle
    On Error Resume Next
    If el.Type = msdElementTypeTextNode Then
        Set subs = el.AsComplexElement.GetSubElements
        Do While subs.MoveNext
            DoiMotChu = DoiMotChu + DoiMotChu(subs.Current, fnt)
        Loop
        Exit Function
    End If
    If el.Type <> msdElementTypeText Then Exit Function
    Set oT = el
    fn = LCase$(oT.TextStyle.Font.Name)
    If Not (Left$(fn, 2) = "vn" Or Left$(fn, 3) = ".vn") Then Exit Function
    s = DC_Tcvn3SangUnicode(oT.Text)
    Err.Clear
    Set ts = oT.TextStyle
    Set ts.Font = fnt
    If Err.Number <> 0 Then Err.Clear: ts.Font = fnt
    Set oT.TextStyle = ts
    If Err.Number <> 0 Then Err.Clear: oT.TextStyle = ts
    oT.Text = s
    Err.Clear
    oT.Rewrite
    If Err.Number = 0 Then DoiMotChu = 1
End Function

Private Function TimFontTen(ByVal ten As String) As Object
    Dim fs As Object, f As Object, i As Long
    On Error Resume Next
    Set fs = ActiveDesignFile.Fonts
    For Each f In fs
        If StrComp(f.Name, ten, vbTextCompare) = 0 Then Set TimFontTen = f: Exit Function
    Next f
    For i = 0 To 1023
        Set f = Nothing
        Set f = fs.Item(i)
        If Not f Is Nothing Then
            If StrComp(f.Name, ten, vbTextCompare) = 0 Then Set TimFontTen = f: Exit Function
        End If
    Next i
End Function

Attribute VB_Name = "modTimLoi"
Option Explicit

'============================================================
' modTimLoi - Tim loi du lieu (5 loai nhu gCadas)
'   D: dinh treo (ho ranh)   S: canh ngan   A: thua nho
'   X: giao diem             O: chong de     E: canh sai (canh cut)
' Ve dau bao loi len level xuat loi (mau khac nhau).
'============================================================

' Doc doan tu NHIEU level (danh sach ten cach nhau boi dau phay)
Public Function LayDoanNhieuLevel(ByVal levelsCSV As String, ByVal snap As Double, _
                                  ByRef minX As Double, ByRef minY As Double, _
                                  ByRef maxX As Double, ByRef maxY As Double, _
                                  Optional ByVal mauCSV As String = "") As Collection
    Dim segs As New Collection
    Dim arr() As String, i As Long, k As Long
    Dim s2 As Collection
    Dim mnx As Double, mny As Double, mxx As Double, mxy As Double
    Dim first As Boolean
    first = True
    arr = Split(levelsCSV, ",")
    For i = LBound(arr) To UBound(arr)
        If Len(Trim$(arr(i))) > 0 Then
            Set s2 = LayCacDoan(snap, Trim$(arr(i)), mnx, mny, mxx, mxy, mauCSV)
            If s2.Count > 0 Then
                For k = 1 To s2.Count
                    segs.Add s2.Item(k)
                Next k
                If first Then
                    minX = mnx: minY = mny: maxX = mxx: maxY = mxy: first = False
                Else
                    If mnx < minX Then minX = mnx
                    If mny < minY Then minY = mny
                    If mxx > maxX Then maxX = mxx
                    If mxy > maxY Then maxY = mxy
                End If
            End If
        End If
    Next i
    Set LayDoanNhieuLevel = segs
End Function

Private Function KcHai(ByVal ax As Double, ByVal ay As Double, _
                       ByVal bx As Double, ByVal by As Double) As Double
    KcHai = Sqr((bx - ax) ^ 2 + (by - ay) ^ 2)
End Function

' Giao diem TRONG (khong tinh dau mut) cua hai doan
Private Function GiaoDiem(ByVal ax As Double, ByVal ay As Double, _
                          ByVal bx As Double, ByVal by As Double, _
                          ByVal cx As Double, ByVal cy As Double, _
                          ByVal dx As Double, ByVal dy As Double, _
                          ByRef ix As Double, ByRef iy As Double) As Boolean
    GiaoDiem = False
    Dim r1x As Double, r1y As Double, r2x As Double, r2y As Double, den As Double
    Dim t As Double, u As Double
    Const EPS As Double = 0.000001
    r1x = bx - ax: r1y = by - ay
    r2x = dx - cx: r2y = dy - cy
    den = r1x * r2y - r1y * r2x
    If Abs(den) < 0.000000000001 Then Exit Function
    t = ((cx - ax) * r2y - (cy - ay) * r2x) / den
    u = ((cx - ax) * r1y - (cy - ay) * r1x) / den
    If t > EPS And t < 1# - EPS And u > EPS And u < 1# - EPS Then
        ix = ax + t * r1x
        iy = ay + t * r1y
        GiaoDiem = True
    End If
End Function


'============================================================
' CHAY TIM LOI
'============================================================
Public Sub ChayTimLoi(ByVal levelsCSV As String, _
                      ByVal cbD As Boolean, ByVal cbS As Boolean, ByVal cbA As Boolean, _
                      ByVal cbX As Boolean, ByVal cbo As Boolean, ByVal cbE As Boolean, _
                      ByVal canhNgan As Double, ByVal thuaNho As Double, _
                      ByVal snap As Double, ByVal levelLoi As String, _
                      Optional ByVal mauCSV As String = "")

    If snap <= 0 Then snap = 0.05
    Dim minX As Double, minY As Double, maxX As Double, maxY As Double
    Dim segs As Collection
    Set segs = LayDoanNhieuLevel(levelsCSV, snap, minX, minY, maxX, maxY, mauCSV)
    If segs.Count = 0 Then
        MsgBox "Khong doc duoc doan nao tu cac level da chon.", vbExclamation, "Tim loi"
        Exit Sub
    End If

    ' Dat level xuat loi lam active (dau bao loi ve len do)
    If Len(Trim$(levelLoi)) > 0 Then
        On Error Resume Next
        ActiveSettings.Level = ActiveModelReference.Levels(Trim$(levelLoi))
        On Error GoTo 0
    End If

    Dim size As Double
    size = ((maxX - minX) + (maxY - minY)) / 2# / 2000#
    If size <= 0 Then size = 0.3

    Dim nD As Long, nS As Long, na As Long, nX As Long, nO As Long, nE As Long
    Dim i As Long, j As Long, s1() As Double, s2() As Double
    Dim dai As Double, mx As Double, my As Double

    ' D: dinh treo (ho ranh)
    If cbD Then
        Dim ho As Collection, p() As Double
        Set ho = TimDiemHo(segs, snap)
        For i = 1 To ho.Count
            p = ho.Item(i)
            VeDanhDauLoi p(0), p(1), size          ' X do
            nD = nD + 1
        Next i
    End If

    ' S: canh ngan
    If cbS Then
        For i = 1 To segs.Count
            s1 = segs.Item(i)
            dai = KcHai(s1(0), s1(1), s1(2), s1(3))
            If dai > 0 And dai < canhNgan Then
                VeTam (s1(0) + s1(2)) / 2#, (s1(1) + s1(3)) / 2#, size, 5
                nS = nS + 1
            End If
        Next i
    End If

    ' A: thua nho
    If cbA Then
        Dim tia As Long, vungs As Collection, v As clsVung
        Set vungs = GhepVung(segs, snap, tia)
        For i = 1 To vungs.Count
            Set v = vungs.Item(i)
            If v.dt < thuaNho Then
                VeTam v.cx, v.cy, size, 6
                na = na + 1
            End If
        Next i
    End If

    ' X: giao diem (trong)
    If cbX Then
        Dim ix As Double, iy As Double
        For i = 1 To segs.Count - 1
            s1 = segs.Item(i)
            For j = i + 1 To segs.Count
                s2 = segs.Item(j)
                If GiaoDiem(s1(0), s1(1), s1(2), s1(3), s2(0), s2(1), s2(2), s2(3), ix, iy) Then
                    VeTam ix, iy, size, 3
                    nX = nX + 1
                End If
            Next j
        Next i
    End If

    ' O: chong de (doan trung nhau)
    If cbo Then
        Dim d As Object, key As String, eA As String, eB As String
        Set d = CreateObject("Scripting.Dictionary")
        For i = 1 To segs.Count
            s1 = segs.Item(i)
            eA = CLng(Round(s1(0) / snap)) & "|" & CLng(Round(s1(1) / snap))
            eB = CLng(Round(s1(2) / snap)) & "|" & CLng(Round(s1(3) / snap))
            If eA <= eB Then key = eA & "_" & eB Else key = eB & "_" & eA
            If d.Exists(key) Then
                VeTam (s1(0) + s1(2)) / 2#, (s1(1) + s1(3)) / 2#, size, 7
                nO = nO + 1
            Else
                d.Add key, True
            End If
        Next i
    End If

    ' E: canh sai (canh co dau mut bac 1 - canh cut/du)
    If cbE Then
        Dim deg As Object, ka As String, kB As String
        Set deg = CreateObject("Scripting.Dictionary")
        For i = 1 To segs.Count
            s1 = segs.Item(i)
            ka = CLng(Round(s1(0) / snap)) & "|" & CLng(Round(s1(1) / snap))
            kB = CLng(Round(s1(2) / snap)) & "|" & CLng(Round(s1(3) / snap))
            deg(ka) = deg(ka) + 1
            deg(kB) = deg(kB) + 1
        Next i
        For i = 1 To segs.Count
            s1 = segs.Item(i)
            ka = CLng(Round(s1(0) / snap)) & "|" & CLng(Round(s1(1) / snap))
            kB = CLng(Round(s1(2) / snap)) & "|" & CLng(Round(s1(3) / snap))
            If deg(ka) = 1 Or deg(kB) = 1 Then
                VeTam (s1(0) + s1(2)) / 2#, (s1(1) + s1(3)) / 2#, size, 2
                nE = nE + 1
            End If
        Next i
    End If

    MsgBox "So doan quet: " & segs.Count & vbCrLf & vbCrLf & _
           "(D) Dinh treo/ho ranh: " & nD & vbCrLf & _
           "(S) Canh ngan: " & nS & vbCrLf & _
           "(A) Thua nho: " & na & vbCrLf & _
           "(X) Giao diem: " & nX & vbCrLf & _
           "(O) Chong de: " & nO & vbCrLf & _
           "(E) Canh sai: " & nE, _
           vbInformation, "Ket qua tim loi"
End Sub

Attribute VB_Name = "modTriDo"
'============================================================
' modTriDo - Xu ly so lieu tri do + kiem tra Topology (kieu LandMap)
'   Menu Ban do > Xu ly so lieu tri do:
'     TDTOADO   Hien thi tri do toa do (ghi X,Y tai dinh doi tuong chon)
'     TDGOCCANH Hien thi tri do goc canh (chieu dai + phuong vi tung canh)
'     TRIENDS   Trien diem theo danh sach (file txt/csv: Ten X Y [H])
'   Menu Ban do > Tao Topology thua dat:
'     CANHNGAN  Tim canh thua qua ngan
'     LAMTRON   Lam tron so le toa do
'     GOCNHO    Tim goc nho, diem thang hang
'   X = Bac (Northing, y ban ve), Y = Dong (Easting, x ban ve) theo quy uoc VN.
'   Loc level theo Level.Number. Chu Times New Roman, net 0.
'============================================================
Option Explicit

Private mFont As Object
Private mDaTimFont As Boolean

Private Function tieuDe() As String
    tieuDe = "Tr" & ChrW(7883) & " " & ChrW(273) & "o / Topology"
End Function

'============================================================
' HIEN THI TRI DO TOA DO
'============================================================
Public Sub DC_TDToaDo()
    Dim dS As Collection, lvSo As Long, cao As Double, le As Long, ok As Boolean
    Set dS = DsChon()
    If dS.Count = 0 Then
        DC_ThongBao "Ch" & ChrW(7885) & "n c" & ChrW(225) & "c th" & ChrW(7917) & "a / " & ChrW(273) & ChrW(432) & ChrW(7901) & "ng ranh c" & ChrW(7847) & "n ghi t" & ChrW(7885) & "a " & ChrW(273) & ChrW(7897) & " tr" & ChrW(432) & ChrW(7899) & "c, r" & ChrW(7891) & "i ch" & ChrW(7841) & "y l" & ChrW(7841) & "i l" & ChrW(7879) & "nh.", tieuDe, vbExclamation
        Exit Sub
    End If
    lvSo = CLng(val(Hoi("Level ghi toa do:", "TD_LV", "30", ok))): If Not ok Then Exit Sub
    cao = val(Hoi("Co chu (m):", "TD_CAO", "1", ok)): If Not ok Then Exit Sub
    le = CLng(val(Hoi("So le toa do:", "TD_LE", "2", ok))): If Not ok Then Exit Sub
    If cao <= 0 Then cao = 1
    If lvSo <= 0 Then lvSo = 30

    Dim lv As Level, i As Long, j As Long, pts() As Point3d, n As Long, daCo As Object, k As String, dem As Long
    Set lv = DC_LevelTheoSo(lvSo)
    Set daCo = CreateObject("Scripting.Dictionary")
    For i = 1 To dS.Count
        n = DinhPhanTu(dS.Item(i), pts)
        For j = 0 To n - 1
            k = Format$(pts(j).x, "0.000") & "|" & Format$(pts(j).y, "0.000")
            If Not daCo.Exists(k) Then
                daCo.Add k, True
                VeVong pts(j).x, pts(j).y, cao * 0.15, lv, -1
                VeChu pts(j).x + cao * 0.4, pts(j).y + cao * 0.2, "X=" & SoLe(pts(j).y, le), cao, 0, lv, msdTextJustificationLeftBottom
                VeChu pts(j).x + cao * 0.4, pts(j).y - cao * 0.2, "Y=" & SoLe(pts(j).x, le), cao, 0, lv, msdTextJustificationLeftTop
                dem = dem + 1
            End If
        Next j
    Next i
    RedrawAllViews
    DC_ThongBao ChrW(272) & ChrW(227) & " ghi t" & ChrW(7885) & "a " & ChrW(273) & ChrW(7897) & " " & dem & " " & ChrW(273) & ChrW(7881) & "nh l" & ChrW(234) & "n level " & lvSo & "." & vbCrLf & "(X = B" & ChrW(7855) & "c, Y = " & ChrW(272) & ChrW(244) & "ng theo VN2000)", tieuDe
End Sub

'============================================================
' HIEN THI TRI DO GOC CANH: chieu dai + phuong vi tung canh
'============================================================
Public Sub DC_TDGocCanh()
    Dim dS As Collection, lvSo As Long, cao As Double, ok As Boolean
    Set dS = DsChon()
    If dS.Count = 0 Then
        DC_ThongBao "Ch" & ChrW(7885) & "n c" & ChrW(225) & "c th" & ChrW(7917) & "a / " & ChrW(273) & ChrW(432) & ChrW(7901) & "ng ranh c" & ChrW(7847) & "n ghi g" & ChrW(243) & "c c" & ChrW(7841) & "nh tr" & ChrW(432) & ChrW(7899) & "c, r" & ChrW(7891) & "i ch" & ChrW(7841) & "y l" & ChrW(7841) & "i l" & ChrW(7879) & "nh.", tieuDe, vbExclamation
        Exit Sub
    End If
    lvSo = CLng(val(Hoi("Level ghi goc canh:", "TD_LVGC", "30", ok))): If Not ok Then Exit Sub
    cao = val(Hoi("Co chu (m):", "TD_CAO", "1", ok)): If Not ok Then Exit Sub
    If cao <= 0 Then cao = 1
    If lvSo <= 0 Then lvSo = 30

    Dim lv As Level, i As Long, j As Long, pts() As Point3d, n As Long, daCo As Object, k As String, dem As Long
    Dim ax As Double, ay As Double, bx As Double, by As Double, dx As Double, dy As Double, L As Double
    Dim mx As Double, my As Double, gocChu As Double, nX As Double, ny As Double
    Set lv = DC_LevelTheoSo(lvSo)
    Set daCo = CreateObject("Scripting.Dictionary")
    For i = 1 To dS.Count
        n = DinhPhanTu(dS.Item(i), pts)
        For j = 0 To n - 2
            ax = pts(j).x: ay = pts(j).y: bx = pts(j + 1).x: by = pts(j + 1).y
            dx = bx - ax: dy = by - ay: L = Sqr(dx * dx + dy * dy)
            If L > 0.001 Then
                k = KhoaCanh(ax, ay, bx, by)
                If Not daCo.Exists(k) Then
                    daCo.Add k, True
                    mx = (ax + bx) / 2: my = (ay + by) / 2
                    gocChu = Atn2(dy, dx)
                    If gocChu > PI() / 2 Or gocChu <= -PI() / 2 Then gocChu = gocChu + PI()
                    nX = -Sin(gocChu): ny = Cos(gocChu)       ' phap tuyen phia tren chu
                    VeChu mx + nX * cao * 0.6, my + ny * cao * 0.6, Format$(L, "0.00"), cao, gocChu, lv, msdTextJustificationCenterCenter
                    VeChu mx - nX * cao * 0.6, my - ny * cao * 0.6, PhuongVi(dx, dy), cao * 0.8, gocChu, lv, msdTextJustificationCenterCenter
                    dem = dem + 1
                End If
            End If
        Next j
    Next i
    RedrawAllViews
    DC_ThongBao ChrW(272) & ChrW(227) & " ghi chi" & ChrW(7873) & "u d" & ChrW(224) & "i + ph" & ChrW(432) & ChrW(417) & "ng v" & ChrW(7883) & " " & dem & " c" & ChrW(7841) & "nh l" & ChrW(234) & "n level " & lvSo & "." & vbCrLf & _
                "(Ph" & ChrW(432) & ChrW(417) & "ng v" & ChrW(7883) & " t" & ChrW(237) & "nh t" & ChrW(7915) & " h" & ChrW(432) & ChrW(7899) & "ng B" & ChrW(7855) & "c, theo chi" & ChrW(7873) & "u kim " & ChrW(273) & ChrW(7891) & "ng h" & ChrW(7891) & ", theo th" & ChrW(7913) & " t" & ChrW(7921) & " " & ChrW(273) & ChrW(7881) & "nh c" & ChrW(7911) & "a " & ChrW(273) & ChrW(7889) & "i t" & ChrW(432) & ChrW(7907) & "ng)", tieuDe
End Sub

' Phuong vi (tu Bac, theo chieu kim dong ho) dang do-phut-giay
Private Function PhuongVi(ByVal dx As Double, ByVal dy As Double) As String
    Dim a As Double, d As Long, m As Long, s As Long, t As Long
    a = Atn2(dx, dy) * 180# / PI()          ' dx = Dong, dy = Bac
    If a < 0 Then a = a + 360#
    t = CLng(a * 3600#)
    If t >= 1296000 Then t = t - 1296000
    d = t \ 3600: m = (t Mod 3600) \ 60: s = t Mod 60
    PhuongVi = d & ChrW(176) & Format$(m, "00") & "'" & Format$(s, "00") & """"
End Function

'============================================================
' TRIEN DIEM THEO DANH SACH (file txt/csv: Ten X Y [H])
'============================================================
Public Sub DC_TrienDiemDS()
    Dim f As String, ok As Boolean, lvSo As Long, cao As Double
    f = CF_ChonMotFile("Danh s" & ChrW(225) & "ch " & ChrW(273) & "i" & ChrW(7875) & "m (*.txt;*.csv)|*.txt;*.csv|T" & ChrW(7845) & "t c" & ChrW(7843) & " (*.*)|*.*", "Ch" & ChrW(7885) & "n file danh s" & ChrW(225) & "ch " & ChrW(273) & "i" & ChrW(7875) & "m (T" & ChrW(234) & "n X Y [H])")
    If Len(f) = 0 Then Exit Sub
    lvSo = CLng(val(Hoi("Level trien diem:", "TD_LVDIEM", "20", ok))): If Not ok Then Exit Sub
    cao = val(Hoi("Co chu ten diem (m):", "TD_CAO", "1", ok)): If Not ok Then Exit Sub
    If cao <= 0 Then cao = 1
    If lvSo <= 0 Then lvSo = 20

    Dim txt As String, Dong() As String, i As Long, p() As String, nP As Long, nBo As Long
    Dim ten As String, a As Double, b As Double, h As String, x As Double, y As Double
    Dim x1 As Double, y1 As Double, x2 As Double, y2 As Double, dau As Boolean, doiTruc As Integer
    txt = DocChu(f)
    If Len(txt) = 0 Then
        DC_ThongBao "Kh" & ChrW(244) & "ng " & ChrW(273) & ChrW(7885) & "c " & ChrW(273) & ChrW(432) & ChrW(7907) & "c file: " & f, tieuDe, vbExclamation
        Exit Sub
    End If
    Dim lv As Level
    Set lv = DC_LevelTheoSo(lvSo)
    Dong = Split(Replace(txt, vbCr, ""), vbLf)
    doiTruc = -1
    For i = 0 To UBound(Dong)
        If TachDong(Dong(i), p) >= 3 Then
            ten = p(0)
            If LaSo(p(1)) And LaSo(p(2)) Then
                a = SoVal(p(1)): b = SoVal(p(2))
                h = "": If UBound(p) >= 3 Then If LaSo(p(3)) Then h = p(3)
                ' VN2000: X(Bac) ~ 1.000.000+ > Y(Dong) ~ 400.000-800.000
                If doiTruc < 0 Then doiTruc = IIf(a > b, 1, 0)
                If doiTruc = 1 Then x = b: y = a Else x = a: y = b
                VeVong x, y, cao * 0.25, lv, -1
                VeChu x + cao * 0.4, y + cao * 0.3, ten, cao, 0, lv, msdTextJustificationLeftBottom
                If Len(h) > 0 Then VeChu x + cao * 0.4, y - cao * 0.3, "h=" & h, cao * 0.8, 0, lv, msdTextJustificationLeftTop
                If Not dau Then
                    x1 = x: x2 = x: y1 = y: y2 = y: dau = True
                Else
                    If x < x1 Then x1 = x
                    If x > x2 Then x2 = x
                    If y < y1 Then y1 = y
                    If y > y2 Then y2 = y
                End If
                nP = nP + 1
            Else
                nBo = nBo + 1
            End If
        ElseIf Len(Trim$(Dong(i))) > 0 Then
            nBo = nBo + 1
        End If
    Next i
    If nP = 0 Then
        DC_ThongBao "Kh" & ChrW(244) & "ng c" & ChrW(243) & " " & ChrW(273) & "i" & ChrW(7875) & "m h" & ChrW(7907) & "p l" & ChrW(7879) & " trong file." & vbCrLf & "M" & ChrW(7895) & "i d" & ChrW(242) & "ng: T" & ChrW(234) & "n X Y [H] (c" & ChrW(225) & "ch nhau b" & ChrW(7857) & "ng tab, d" & ChrW(7845) & "u ch" & ChrW(7845) & "m ph" & ChrW(7849) & "y, d" & ChrW(7845) & "u ph" & ChrW(7849) & "y ho" & ChrW(7863) & "c kho" & ChrW(7843) & "ng tr" & ChrW(7855) & "ng).", tieuDe, vbExclamation
        Exit Sub
    End If
    Dim d As Double
    d = (x2 - x1): If y2 - y1 > d Then d = y2 - y1
    If d < 20 Then d = 20
    DC_ZoomVung (x1 + x2) / 2 - d * 0.6, (y1 + y2) / 2 - d * 0.6, (x1 + x2) / 2 + d * 0.6, (y1 + y2) / 2 + d * 0.6
    DC_ThongBao ChrW(272) & ChrW(227) & " tri" & ChrW(7875) & "n " & nP & " " & ChrW(273) & "i" & ChrW(7875) & "m l" & ChrW(234) & "n level " & lvSo & "." & IIf(nBo > 0, vbCrLf & "B" & ChrW(7887) & " qua " & nBo & " d" & ChrW(242) & "ng kh" & ChrW(244) & "ng h" & ChrW(7907) & "p l" & ChrW(7879) & " (ti" & ChrW(234) & "u " & ChrW(273) & ChrW(7873) & "...).", ""), tieuDe
End Sub

Private Function TachDong(ByVal s As String, ByRef p() As String) As Long
    Dim t As String, a() As String, i As Long, n As Long
    t = Trim$(s)
    If Len(t) = 0 Then Exit Function
    If InStr(t, vbTab) > 0 Then
        t = Replace(t, vbTab, ";")
    ElseIf InStr(t, ";") = 0 And InStr(t, ",") > 0 And InStr(t, " ") = 0 Then
        t = Replace(t, ",", ";")
    ElseIf InStr(t, ";") = 0 Then
        Do While InStr(t, "  ") > 0: t = Replace(t, "  ", " "): Loop
        t = Replace(t, " ", ";")
    End If
    a = Split(t, ";")
    ReDim p(0 To UBound(a))
    For i = 0 To UBound(a)
        If Len(Trim$(a(i))) > 0 Then p(n) = Trim$(a(i)): n = n + 1
    Next i
    If n = 0 Then Exit Function
    ReDim Preserve p(0 To n - 1)
    TachDong = n
End Function

Private Function LaSo(ByVal s As String) As Boolean
    Dim t As String
    t = Replace(Trim$(s), ",", ".")
    If Len(t) = 0 Then Exit Function
    LaSo = (t Like "*#*") And Not (t Like "*[!0-9.+-]*")
End Function

Private Function SoVal(ByVal s As String) As Double
    SoVal = val(Replace(Trim$(s), ",", "."))
End Function

Private Function DocChu(ByVal f As String) As String
    Dim st As Object
    On Error Resume Next
    Set st = CreateObject("ADODB.Stream")
    st.Type = 2: st.Charset = "utf-8": st.Open
    st.LoadFromFile f
    DocChu = st.ReadText(-1)
    st.Close
    If Len(DocChu) > 0 Then
        If AscW(Left$(DocChu, 1)) = &HFEFF Then DocChu = Mid$(DocChu, 2)
    End If
End Function

'============================================================
' TIM CANH THUA QUA NGAN
'============================================================
Public Sub DC_TimCanhNgan()
    Dim lvs() As Long, nLv As Long, Lmin As Double, lvLoi As Long, ok As Boolean
    nLv = DC_DsSoLevel(Hoi("Cac level ranh thua (vd 10,23):", "TD_LVRANH", LvHienTai(), ok), lvs): If Not ok Then Exit Sub
    If nLv = 0 Then DC_ThongBao "Ch" & ChrW(432) & "a nh" & ChrW(7853) & "p level ranh.", tieuDe, vbExclamation: Exit Sub
    Lmin = val(Hoi("Canh ngan hon (m):", "TD_CANHMIN", "0.2", ok)): If Not ok Then Exit Sub
    lvLoi = CLng(val(Hoi("Level danh dau loi:", "TD_LVLOI", "63", ok))): If Not ok Then Exit Sub
    If Lmin <= 0 Then Lmin = 0.2
    If lvLoi <= 0 Then lvLoi = 63

    Dim chuoi As Collection, i As Long, j As Long, d() As Double, n As Long, daCo As Object, k As String
    Dim dx As Double, dy As Double, L As Double, dem As Long, lv As Level, r As Double
    Dim fx As Double, fy As Double, ax As Double, ay As Double, bx As Double, by As Double
    Set chuoi = ChuoiTheoLevel(lvs, nLv)
    Set lv = DC_LevelTheoSo(lvLoi)
    Set daCo = CreateObject("Scripting.Dictionary")
    r = Lmin * 2: If r < 0.5 Then r = 0.5
    For i = 1 To chuoi.Count
        d = chuoi.Item(i): n = (UBound(d) + 1) \ 2
        For j = 0 To n - 2
            ax = d(2 * j): ay = d(2 * j + 1): bx = d(2 * j + 2): by = d(2 * j + 3)
            dx = bx - ax: dy = by - ay
            L = Sqr(dx * dx + dy * dy)
            If L > 0.0005 And L < Lmin Then
                k = KhoaCanh(ax, ay, bx, by)
                If Not daCo.Exists(k) Then
                    daCo.Add k, True
                    VeVong (ax + bx) / 2, (ay + by) / 2, r, lv, 3
                    VeChu (ax + bx) / 2 + r, (ay + by) / 2 + r, Format$(L, "0.000"), r * 0.8, 0, lv, msdTextJustificationLeftBottom
                    If dem = 0 Then fx = (ax + bx) / 2: fy = (ay + by) / 2
                    dem = dem + 1
                End If
            End If
        Next j
    Next i
    RedrawAllViews
    If dem = 0 Then
        DC_ThongBao "Kh" & ChrW(244) & "ng c" & ChrW(243) & " c" & ChrW(7841) & "nh n" & ChrW(224) & "o ng" & ChrW(7855) & "n h" & ChrW(417) & "n " & Lmin & " m.", tieuDe
    Else
        If DC_ThongBao("T" & ChrW(236) & "m th" & ChrW(7845) & "y " & dem & " c" & ChrW(7841) & "nh ng" & ChrW(7855) & "n h" & ChrW(417) & "n " & Lmin & " m (khoanh tr" & ChrW(242) & "n " & ChrW(273) & ChrW(7887) & " tr" & ChrW(234) & "n level " & lvLoi & ")." & vbCrLf & vbCrLf & _
                       "Zoom t" & ChrW(7899) & "i c" & ChrW(7841) & "nh " & ChrW(273) & ChrW(7847) & "u ti" & ChrW(234) & "n?", tieuDe, vbYesNo Or vbQuestion) = vbYes Then
            DC_ZoomVung fx - r * 10, fy - r * 10, fx + r * 10, fy + r * 10
        End If
    End If
End Sub

'============================================================
' TIM GOC NHO, DIEM THANG HANG
'============================================================
Public Sub DC_TimGocNho()
    Dim lvs() As Long, nLv As Long, gMin As Double, gTH As Double, lvLoi As Long, ok As Boolean
    nLv = DC_DsSoLevel(Hoi("Cac level ranh thua (vd 10,23):", "TD_LVRANH", LvHienTai(), ok), lvs): If Not ok Then Exit Sub
    If nLv = 0 Then DC_ThongBao "Ch" & ChrW(432) & "a nh" & ChrW(7853) & "p level ranh.", tieuDe, vbExclamation: Exit Sub
    gMin = val(Hoi("Goc nho hon (do):", "TD_GOCMIN", "15", ok)): If Not ok Then Exit Sub
    gTH = val(Hoi("Thang hang: lech duoi (do):", "TD_GOCTH", "1", ok)): If Not ok Then Exit Sub
    lvLoi = CLng(val(Hoi("Level danh dau loi:", "TD_LVLOI", "63", ok))): If Not ok Then Exit Sub
    If gMin <= 0 Then gMin = 15
    If gTH <= 0 Then gTH = 1
    If lvLoi <= 0 Then lvLoi = 63

    Dim chuoi As Collection, i As Long, j As Long, d() As Double, n As Long, daCo As Object, k As String
    Dim kin As Boolean, ip As Long, inx As Long, g As Double, lv As Level, r As Double
    Dim nNho As Long, nTH As Long, fx As Double, fy As Double, coF As Boolean, px As Double, py As Double
    Set chuoi = ChuoiTheoLevel(lvs, nLv)
    Set lv = DC_LevelTheoSo(lvLoi)
    Set daCo = CreateObject("Scripting.Dictionary")
    r = 0.5
    For i = 1 To chuoi.Count
        d = chuoi.Item(i): n = (UBound(d) + 1) \ 2
        If n >= 3 Then
            kin = (Abs(d(0) - d(2 * n - 2)) < 0.001 And Abs(d(1) - d(2 * n - 1)) < 0.001)
            If kin Then n = n - 1            ' bo dinh lap cuoi
            For j = 0 To n - 1
                If kin Or (j > 0 And j < n - 1) Then
                    ip = j - 1: If ip < 0 Then ip = n - 1
                    inx = j + 1: If inx > n - 1 Then inx = 0
                    px = d(2 * j): py = d(2 * j + 1)
                    g = GocTai(d(2 * ip), d(2 * ip + 1), px, py, d(2 * inx), d(2 * inx + 1))
                    If g >= 0 Then
                        k = Format$(px, "0.000") & "|" & Format$(py, "0.000")
                        If g < gMin Then
                            If Not daCo.Exists(k) Then
                                daCo.Add k, True
                                VeVong px, py, r, lv, 3
                                VeChu px + r, py + r, Format$(g, "0.0") & ChrW(176), r * 0.8, 0, lv, msdTextJustificationLeftBottom
                                nNho = nNho + 1
                                If Not coF Then fx = px: fy = py: coF = True
                            End If
                        ElseIf g > 180 - gTH Then
                            If Not daCo.Exists(k) Then
                                daCo.Add k, True
                                VeVong px, py, r, lv, 4
                                nTH = nTH + 1
                                If Not coF Then fx = px: fy = py: coF = True
                            End If
                        End If
                    End If
                End If
            Next j
        End If
    Next i
    RedrawAllViews
    If nNho + nTH = 0 Then
        DC_ThongBao "Kh" & ChrW(244) & "ng c" & ChrW(243) & " g" & ChrW(243) & "c nh" & ChrW(7887) & " h" & ChrW(417) & "n " & gMin & ChrW(176) & " hay " & ChrW(273) & "i" & ChrW(7875) & "m th" & ChrW(7859) & "ng h" & ChrW(224) & "ng.", tieuDe
    Else
        If DC_ThongBao("G" & ChrW(243) & "c nh" & ChrW(7887) & " (< " & gMin & ChrW(176) & "): " & nNho & " (khoanh " & ChrW(273) & ChrW(7887) & ")" & vbCrLf & _
                       ChrW(272) & "i" & ChrW(7875) & "m th" & ChrW(7859) & "ng h" & ChrW(224) & "ng (l" & ChrW(7879) & "ch < " & gTH & ChrW(176) & "): " & nTH & " (khoanh v" & ChrW(224) & "ng)" & vbCrLf & _
                       ChrW(272) & ChrW(225) & "nh d" & ChrW(7845) & "u tr" & ChrW(234) & "n level " & lvLoi & "." & vbCrLf & vbCrLf & "Zoom t" & ChrW(7899) & "i " & ChrW(273) & "i" & ChrW(7875) & "m " & ChrW(273) & ChrW(7847) & "u ti" & ChrW(234) & "n?", tieuDe, vbYesNo Or vbQuestion) = vbYes Then
            DC_ZoomVung fx - 10, fy - 10, fx + 10, fy + 10
        End If
    End If
End Sub

' Goc tai B giua BA va BC (do, 0..180); -1 neu canh suy bien
Private Function GocTai(ByVal ax As Double, ByVal ay As Double, ByVal bx As Double, ByVal by As Double, _
                        ByVal cx As Double, ByVal cy As Double) As Double
    Dim ux As Double, uy As Double, vx As Double, vy As Double, lu As Double, lw As Double, cs As Double
    ux = ax - bx: uy = ay - by: vx = cx - bx: vy = cy - by
    lu = Sqr(ux * ux + uy * uy): lw = Sqr(vx * vx + vy * vy)
    GocTai = -1
    If lu < 0.0005 Or lw < 0.0005 Then Exit Function
    cs = (ux * vx + uy * vy) / (lu * lw)
    If cs > 1 Then cs = 1
    If cs < -1 Then cs = -1
    GocTai = Atn2(Sqr(1 - cs * cs), cs) * 180# / PI()
End Function

'============================================================
' LAM TRON SO LE TOA DO (dinh line/linestring/shape tren cac level)
'============================================================
Public Sub DC_LamTronToaDo()
    Dim lvs() As Long, nLv As Long, le As Long, ok As Boolean
    nLv = DC_DsSoLevel(Hoi("Cac level can lam tron (vd 10,23):", "TD_LVRANH", LvHienTai(), ok), lvs): If Not ok Then Exit Sub
    If nLv = 0 Then DC_ThongBao "Ch" & ChrW(432) & "a nh" & ChrW(7853) & "p level.", tieuDe, vbExclamation: Exit Sub
    le = CLng(val(Hoi("So le giu lai (0-4):", "TD_LELT", "2", ok))): If Not ok Then Exit Sub
    If le < 0 Then le = 0
    If le > 4 Then le = 4
    If DC_ThongBao("L" & ChrW(224) & "m tr" & ChrW(242) & "n t" & ChrW(7885) & "a " & ChrW(273) & ChrW(7897) & " " & ChrW(273) & ChrW(7881) & "nh c" & ChrW(225) & "c " & ChrW(273) & ChrW(432) & ChrW(7901) & "ng / v" & ChrW(249) & "ng tr" & ChrW(234) & "n level " & DsLvChu(lvs, nLv) & " v" & ChrW(7873) & " " & le & " s" & ChrW(7889) & " l" & ChrW(7867) & "." & vbCrLf & _
                   "B" & ChrW(7843) & "n v" & ChrW(7869) & " s" & ChrW(7869) & " b" & ChrW(7883) & " s" & ChrW(7917) & "a v" & ChrW(224) & " KH" & ChrW(212) & "NG ho" & ChrW(224) & "n t" & ChrW(225) & "c " & ChrW(273) & ChrW(432) & ChrW(7907) & "c b" & ChrW(7857) & "ng undo mark - n" & ChrW(234) & "n l" & ChrW(432) & "u b" & ChrW(7843) & "n sao tr" & ChrW(432) & ChrW(7899) & "c." & vbCrLf & vbCrLf & "Ti" & ChrW(7871) & "p t" & ChrW(7909) & "c?", _
                   tieuDe, vbYesNo Or vbExclamation) <> vbYes Then Exit Sub

    Dim ee As ElementEnumerator, el As Element, dS As New Collection, i As Long
    Dim pts() As Point3d, j As Long, doi As Boolean, nSua As Long, nDinh As Long, nBo As Long
    Dim p As Point3d
    Set ee = QuetDuong()
    If ee Is Nothing Then Exit Sub
    Do While ee.MoveNext
        If CoLevel(ee.Current, lvs, nLv) Then dS.Add ee.Current
    Loop
    On Error Resume Next
    For i = 1 To dS.Count
        Set el = dS.Item(i)
        Select Case el.Type
        Case msdElementTypeLine, msdElementTypeLineString, msdElementTypeShape
            Err.Clear
            If el.Type = msdElementTypeShape Then pts = el.AsShapeElement.GetVertices Else pts = el.AsLineElement.GetVertices
            If Err.Number = 0 Then
                doi = False
                For j = LBound(pts) To UBound(pts)
                    p = pts(j)
                    p.x = Tron(p.x, le): p.y = Tron(p.y, le)
                    If p.x <> pts(j).x Or p.y <> pts(j).y Then
                        If el.Type = msdElementTypeShape Then
                            el.AsShapeElement.ModifyVertex j - LBound(pts), p
                        Else
                            el.AsLineElement.ModifyVertex j - LBound(pts), p
                        End If
                        doi = True: nDinh = nDinh + 1
                    End If
                Next j
                If doi Then
                    el.Rewrite
                    If Err.Number = 0 Then nSua = nSua + 1 Else nBo = nBo + 1
                End If
            Else
                nBo = nBo + 1
            End If
        Case Else
            nBo = nBo + 1
        End Select
    Next i
    On Error GoTo 0
    RedrawAllViews
    DC_ThongBao ChrW(272) & ChrW(227) & " l" & ChrW(224) & "m tr" & ChrW(242) & "n " & nDinh & " " & ChrW(273) & ChrW(7881) & "nh tr" & ChrW(234) & "n " & nSua & " " & ChrW(273) & ChrW(7889) & "i t" & ChrW(432) & ChrW(7907) & "ng." & _
                IIf(nBo > 0, vbCrLf & "B" & ChrW(7887) & " qua " & nBo & " " & ChrW(273) & ChrW(7889) & "i t" & ChrW(432) & ChrW(7907) & "ng (" & ChrW(273) & ChrW(432) & ChrW(7901) & "ng ph" & ChrW(7913) & "c, cung tr" & ChrW(242) & "n ho" & ChrW(7863) & "c l" & ChrW(7895) & "i ghi).", ""), tieuDe
End Sub

Private Function Tron(ByVal v As Double, ByVal le As Long) As Double
    Dim f As Double
    f = 10# ^ le
    Tron = Int(v * f + 0.5) / f
End Function

'============================================================
' DUNG CHUNG
'============================================================
Private Function Hoi(ByVal nhac As String, ByVal khoa As String, ByVal macDinh As String, ByRef ok As Boolean) As String
    Dim s As String
    s = InputBox(nhac, "DiaChinhVL", DC_DocCauHinh(khoa, macDinh))
    ok = (StrPtr(s) <> 0)
    If ok Then DC_GhiCauHinh khoa, s
    Hoi = s
End Function

Private Function LvHienTai() As String
    On Error Resume Next
    LvHienTai = CStr(ActiveSettings.Level.Number)
End Function

Private Function DsLvChu(ByRef lvs() As Long, ByVal n As Long) As String
    Dim i As Long
    For i = 0 To n - 1
        DsLvChu = DsLvChu & IIf(i > 0, ",", "") & lvs(i)
    Next i
End Function

Private Function CoLevel(ByVal el As Element, ByRef lvs() As Long, ByVal n As Long) As Boolean
    Dim i As Long, s As Long
    s = DC_LevelSo(el)
    For i = 0 To n - 1
        If lvs(i) = s Then CoLevel = True: Exit Function
    Next i
End Function

Private Function QuetDuong() As ElementEnumerator
    Dim esc As ElementScanCriteria
    On Error Resume Next
    Set esc = New ElementScanCriteria
    esc.ExcludeAllTypes
    esc.IncludeType msdElementTypeLine
    esc.IncludeType msdElementTypeLineString
    esc.IncludeType msdElementTypeShape
    esc.IncludeType msdElementTypeComplexString
    esc.IncludeType msdElementTypeComplexShape
    Set QuetDuong = ActiveModelReference.Scan(esc)
End Function

' Moi phan tu tren cac level -> 1 chuoi dinh (Double phang x0,y0,x1,y1...) trong Collection
Private Function ChuoiTheoLevel(ByRef lvs() As Long, ByVal nLv As Long) As Collection
    Dim kq As New Collection, ee As ElementEnumerator, pts() As Point3d, n As Long
    Set ChuoiTheoLevel = kq
    Set ee = QuetDuong()
    If ee Is Nothing Then Exit Function
    Do While ee.MoveNext
        If CoLevel(ee.Current, lvs, nLv) Then
            n = DinhPhanTu(ee.Current, pts)
            If n >= 2 Then kq.Add Phang(pts, n)
        End If
    Loop
End Function

' Cac phan tu dang chon (chi loai duong / vung)
Private Function DsChon() As Collection
    Dim kq As New Collection, ee As ElementEnumerator, t As Long
    Set DsChon = kq
    On Error Resume Next
    Set ee = ActiveModelReference.GetSelectedElements
    If ee Is Nothing Then Exit Function
    Do While ee.MoveNext
        t = ee.Current.Type
        If t = msdElementTypeLine Or t = msdElementTypeLineString Or t = msdElementTypeShape Or _
           t = msdElementTypeComplexString Or t = msdElementTypeComplexShape Then kq.Add ee.Current
    Loop
End Function

' Dinh cua 1 phan tu (noi cac phan con cua duong phuc, bo dinh trung lien ke). Tra ve so dinh.
Private Function DinhPhanTu(ByVal el As Element, ByRef pts() As Point3d) As Long
    Dim kq() As Point3d, n As Long, subs As ElementEnumerator, p() As Point3d, i As Long
    ReDim kq(0 To 0)
    On Error Resume Next
    Select Case el.Type
    Case msdElementTypeLine, msdElementTypeLineString
        p = el.AsLineElement.GetVertices
        If Err.Number = 0 Then ThemDinh kq, n, p
    Case msdElementTypeShape
        p = el.AsShapeElement.GetVertices
        If Err.Number = 0 Then ThemDinh kq, n, p
    Case msdElementTypeComplexString, msdElementTypeComplexShape
        Set subs = el.AsComplexElement.GetSubElements
        Do While subs.MoveNext
            Err.Clear
            Select Case subs.Current.Type
            Case msdElementTypeLine, msdElementTypeLineString
                p = subs.Current.AsLineElement.GetVertices
                If Err.Number = 0 Then ThemDinh kq, n, p
            Case msdElementTypeShape
                p = subs.Current.AsShapeElement.GetVertices
                If Err.Number = 0 Then ThemDinh kq, n, p
            End Select
        Loop
    End Select
    If n = 0 Then DinhPhanTu = 0: Exit Function
    ReDim Preserve kq(0 To n - 1)
    pts = kq
    DinhPhanTu = n
End Function

Private Function Phang(ByRef pts() As Point3d, ByVal n As Long) As Double()
    Dim d() As Double, i As Long
    ReDim d(0 To 2 * n - 1)
    For i = 0 To n - 1
        d(2 * i) = pts(i).x: d(2 * i + 1) = pts(i).y
    Next i
    Phang = d
End Function

Private Sub ThemDinh(ByRef kq() As Point3d, ByRef n As Long, ByRef p() As Point3d)
    Dim i As Long
    For i = LBound(p) To UBound(p)
        If n > 0 Then
            If Abs(kq(n - 1).x - p(i).x) < 0.0005 And Abs(kq(n - 1).y - p(i).y) < 0.0005 Then GoTo tiep
        End If
        If n > UBound(kq) Then ReDim Preserve kq(0 To n * 2 + 8)
        kq(n) = p(i): n = n + 1
tiep:
    Next i
End Sub

Private Function KhoaCanh(ByVal ax As Double, ByVal ay As Double, ByVal bx As Double, ByVal by As Double) As String
    Dim a As String, b As String
    a = Format$(ax, "0.000") & "|" & Format$(ay, "0.000")
    b = Format$(bx, "0.000") & "|" & Format$(by, "0.000")
    If a < b Then KhoaCanh = a & "#" & b Else KhoaCanh = b & "#" & a
End Function

Private Function SoLe(ByVal v As Double, ByVal le As Long) As String
    If le <= 0 Then SoLe = Format$(v, "0") Else SoLe = Format$(v, "0." & String$(le, "0"))
End Function

Private Function PI() As Double
    PI = 4# * Atn(1#)
End Function

' atan2(y, x)
Private Function Atn2(ByVal y As Double, ByVal x As Double) As Double
    If x > 0 Then
        Atn2 = Atn(y / x)
    ElseIf x < 0 Then
        If y >= 0 Then Atn2 = Atn(y / x) + PI() Else Atn2 = Atn(y / x) - PI()
    Else
        If y > 0 Then Atn2 = PI() / 2 Else If y < 0 Then Atn2 = -PI() / 2 Else Atn2 = 0
    End If
End Function

Private Function FontVN() As Object
    Dim f As Object
    If mDaTimFont Then Set FontVN = mFont: Exit Function
    mDaTimFont = True
    On Error Resume Next
    For Each f In ActiveDesignFile.Fonts
        If StrComp(f.Name, DC_FONT_VIET, vbTextCompare) = 0 Then Set mFont = f: Exit For
    Next f
    Set FontVN = mFont
End Function

' Ve chu (goc rad), level lv, mau (-1 = mac dinh), Times New Roman, net 0
Private Sub VeChu(ByVal x As Double, ByVal y As Double, ByVal s As String, ByVal cao As Double, _
                  ByVal goc As Double, ByVal lv As Level, ByVal canh As Long, Optional ByVal mau As Long = -1)
    Dim t As TextElement, ts As TextStyle, f As Object
    On Error Resume Next
    Set t = CreateTextElement1(Nothing, s, Point3dFromXYZ(x, y, 0#), Matrix3dFromAxisAndRotationAngle(2, goc))
    If t Is Nothing Then Exit Sub
    Set ts = t.TextStyle
    ts.Height = cao: ts.Width = cao
    ts.Justification = canh
    Set f = FontVN()
    If Not f Is Nothing Then Set ts.Font = f
    Set t.TextStyle = ts
    If Err.Number <> 0 Then Err.Clear: t.TextStyle = ts
    If Not lv Is Nothing Then Set t.Level = lv
    If mau >= 0 Then t.color = mau
    t.LineWeight = 0
    ActiveModelReference.AddElement t
End Sub

Private Sub VeVong(ByVal x As Double, ByVal y As Double, ByVal r As Double, ByVal lv As Level, ByVal mau As Long)
    Dim e As EllipseElement
    On Error Resume Next
    Set e = CreateEllipseElement2(Nothing, Point3dFromXYZ(x, y, 0#), r, r, Matrix3dIdentity)
    If e Is Nothing Then Exit Sub
    If Not lv Is Nothing Then Set e.Level = lv
    If mau >= 0 Then e.color = mau
    e.LineWeight = 0
    ActiveModelReference.AddElement e
End Sub

Attribute VB_Name = "modTrichLuc"
Option Explicit

'============================================================
' modTrichLuc - Trich luc TT26 (muc 1): so do thua + bang toa do + khung
' Toa do doc theo met (uor_m = 1). Bang toa do VN2000:
'   cot X = northing = Y ban ve ; cot Y = easting = X ban ve.
'============================================================


' Moc dinh thua: o vuong nho
Public Sub VeMoc(ByVal x As Double, ByVal y As Double, ByVal r As Double, _
                 Optional ByVal color As Long = -1)
    VeLine x - r, y - r, x + r, y - r, color
    VeLine x + r, y - r, x + r, y + r, color
    VeLine x + r, y + r, x - r, y + r, color
    VeLine x - r, y + r, x - r, y - r, color
End Sub


' Ve so do thua: canh + moc + so hieu dinh + chieu dai canh
Public Sub VeSoDoThua(ByVal v As clsVung, ByVal cao As Double, _
                      Optional ByVal color As Long = -1)
    Dim ring() As Double, n As Long, i As Long
    ring = v.ring
    n = UBound(ring, 1)             ' so dinh phan biet
    If n < 3 Then Exit Sub

    Dim rMoc As Double, OFF As Double
    rMoc = cao * 0.5
    OFF = rMoc * 1.6

    ' Canh thua
    For i = 0 To n - 1
        VeLine ring(i, 0), ring(i, 1), ring(i + 1, 0), ring(i + 1, 1), color
    Next i
    ' Canh cac lo dao
    Dim k As Long, dr() As Double, m As Long
    For k = 1 To v.dao.Count
        dr = v.dao.Item(k)
        m = UBound(dr, 1)
        For i = 0 To m - 1
            VeLine dr(i, 0), dr(i, 1), dr(i + 1, 0), dr(i + 1, 1), color
        Next i
    Next k

    ' Moc + so hieu dinh
    For i = 0 To n - 1
        VeMoc ring(i, 0), ring(i, 1), rMoc, color
        VeText ring(i, 0) + OFF, ring(i, 1) + OFF, CStr(i + 1), cao, color
    Next i

    ' Chieu dai canh (giua canh)
    Dim mx As Double, my As Double, dai As Double
    For i = 0 To n - 1
        mx = (ring(i, 0) + ring(i + 1, 0)) / 2#
        my = (ring(i, 1) + ring(i + 1, 1)) / 2#
        dai = Sqr((ring(i + 1, 0) - ring(i, 0)) ^ 2 + (ring(i + 1, 1) - ring(i, 1)) ^ 2)
        VeText mx, my, Format$(dai, "0.00"), cao, color
    Next i
End Sub


' Ve bang toa do: STT | X | Y | Canh. Goc tren-trai tai (x0, y0).
Public Sub VeBangToaDo(ByVal v As clsVung, ByVal X0 As Double, ByVal Y0 As Double, _
                       ByVal cao As Double, Optional ByVal color As Long = -1)
    Dim ring() As Double, n As Long, i As Long
    ring = v.ring
    n = UBound(ring, 1)
    If n < 3 Then Exit Sub

    Dim Dong As Double
    Dong = cao * 1.8
    Dim cols(0 To 3) As Double
    cols(0) = cao * 3#      ' TT
    cols(1) = cao * 9#      ' X
    cols(2) = cong_X_Y(cao) ' Y
    cols(3) = cao * 6#      ' Canh
    Dim tongRong As Double, c As Long
    tongRong = 0
    For c = 0 To 3
        tongRong = tongRong + cols(c)
    Next c
    Dim soDong As Long
    soDong = n + 1          ' 1 tieu de + n dinh

    ' Duong ngang
    Dim y As Double, r As Long
    y = Y0
    For r = 0 To soDong
        VeLine X0, y, X0 + tongRong, y, color
        y = y - Dong
    Next r
    ' Duong doc
    Dim x As Double
    x = X0
    For c = 0 To 4
        VeLine x, Y0, x, Y0 - soDong * Dong, color
        If c < 4 Then x = x + cols(c)
    Next c

    ' Tieu de
    Dim tieuDe(0 To 3) As String
    tieuDe(0) = "TT": tieuDe(1) = "X (m)": tieuDe(2) = "Y (m)": tieuDe(3) = "Canh (m)"
    OText X0, Y0, cols, 0, tieuDe, Dong, cao, color

    ' Cac dinh
    Dim gia(0 To 3) As String, dai As Double
    For i = 0 To n - 1
        gia(0) = CStr(i + 1)
        gia(1) = Format$(ring(i, 1), "0.00")   ' X_vn = Y ban ve (northing)
        gia(2) = Format$(ring(i, 0), "0.00")   ' Y_vn = X ban ve (easting)
        dai = Sqr((ring(i + 1, 0) - ring(i, 0)) ^ 2 + (ring(i + 1, 1) - ring(i, 1)) ^ 2)
        gia(3) = Format$(dai, "0.00")
        OText X0, Y0, cols, i + 1, gia, Dong, cao, color
    Next i
End Sub

Private Function cong_X_Y(ByVal cao As Double) As Double
    cong_X_Y = cao * 9#
End Function

' Ghi 1 hang o bang (canh giua tung o). rowIndex 0 = tieu de.
Private Sub OText(ByVal X0 As Double, ByVal Y0 As Double, ByRef cols() As Double, _
                  ByVal rowIndex As Long, ByRef vals() As String, _
                  ByVal Dong As Double, ByVal cao As Double, ByVal color As Long)
    Dim cx As Double, cyRow As Double, ci As Long
    cx = X0
    cyRow = Y0 - rowIndex * Dong - Dong / 2#     ' giua o hang
    For ci = 0 To UBound(vals)
        VeText cx + cols(ci) / 2#, cyRow, vals(ci), cao, color
        cx = cx + cols(ci)
    Next ci
End Sub


' Ve khung bao quanh thua (co le). Tra ve goc tren-phai qua ByRef.
Public Sub VeKhungTrichLuc(ByVal v As clsVung, ByVal le As Double, _
                           ByRef x2 As Double, ByRef y2 As Double, _
                           Optional ByVal color As Long = -1)
    Dim ring() As Double, n As Long, i As Long
    ring = v.ring
    n = UBound(ring, 1)
    Dim xmin As Double, xmax As Double, ymin As Double, ymax As Double
    xmin = ring(0, 0): xmax = ring(0, 0): ymin = ring(0, 1): ymax = ring(0, 1)
    For i = 1 To n - 1
        If ring(i, 0) < xmin Then xmin = ring(i, 0)
        If ring(i, 0) > xmax Then xmax = ring(i, 0)
        If ring(i, 1) < ymin Then ymin = ring(i, 1)
        If ring(i, 1) > ymax Then ymax = ring(i, 1)
    Next i
    Dim x1 As Double, y1 As Double
    x1 = xmin - le: y1 = ymin - le
    x2 = xmax + le: y2 = ymax + le
    VeLine x1, y1, x2, y1, color
    VeLine x2, y1, x2, y2, color
    VeLine x2, y2, x1, y2, color
    VeLine x1, y2, x1, y1, color
End Sub


Private Function TenLevelActive() As String
    On Error Resume Next
    TenLevelActive = ActiveSettings.Level.Name
    On Error GoTo 0
End Function


'============================================================
' LENH: TRICH LUC 1 THUA THEO SO THUA
'============================================================
Public Sub DC_TrichLucThua()
    Dim lvRanh As String, lvSo As String, snapStr As String, snap As Double
    lvRanh = InputBox("TEN level RANH thua:", "Trich luc", TenLevelActive())
    lvSo = InputBox("TEN level SO THUA:", "Trich luc", "")
    snapStr = InputBox("Dung sai noi diem (snap):", "Trich luc", "0.05")
    If snapStr = "" Then Exit Sub
    snap = val(snapStr)
    If snap <= 0 Then snap = 0.05

    Dim minX As Double, minY As Double, maxX As Double, maxY As Double
    Dim segs As Collection
    Set segs = LayCacDoan(snap, lvRanh, minX, minY, maxX, maxY)
    If segs.Count = 0 Then
        MsgBox "Khong doc duoc ranh.", vbExclamation, "Trich luc": Exit Sub
    End If
    Dim soTia As Long, vungs As Collection
    Set vungs = GhepVung(segs, snap, soTia)
    GanTruong vungs, lvSo, "so_thua"

    Dim st As String
    st = Trim$(InputBox("So thua can trich luc:", "Trich luc", ""))
    If st = "" Then Exit Sub

    Dim i As Long, v As clsVung, found As clsVung
    Set found = Nothing
    For i = 1 To vungs.Count
        Set v = vungs.Item(i)
        If Trim$(v.soThua) = st Then Set found = v: Exit For
    Next i
    If found Is Nothing Then
        MsgBox "Khong tim thay thua so: " & st, vbExclamation, "Trich luc": Exit Sub
    End If

    ' Co chu
    Dim caoStr As String, cao As Double
    Dim r() As Double, w As Double, h As Double
    r = found.ring
    w = maxX - minX: h = maxY - minY
    cao = ((found_w(found)) + (found_h(found))) / 2# / 40#
    If cao <= 0 Then cao = 1
    caoStr = InputBox("Co chu trich luc:", "Trich luc", Format$(cao, "0.###"))
    If caoStr <> "" Then cao = val(caoStr)
    If cao <= 0 Then cao = 1

    ' Ve: khung -> so do -> nhan -> bang toa do (ben phai khung)
    Dim kx2 As Double, ky2 As Double, le As Double
    le = cao * 6#
    VeKhungTrichLuc found, le, kx2, ky2, 0
    VeSoDoThua found, cao, 0
    VeNhanThuaDayDu found, cao, "khong"
    VeBangToaDo found, kx2 + cao * 3#, ky2, cao, 0

    MsgBox "Da trich luc thua so " & st & _
           " (dien tich " & Format$(Round(found.dt, 1), "0.0") & " m2).", _
           vbInformation, "Trich luc"
End Sub

Private Function found_w(ByVal v As clsVung) As Double
    Dim r() As Double, n As Long, i As Long, a As Double, b As Double
    r = v.ring: n = UBound(r, 1)
    a = r(0, 0): b = r(0, 0)
    For i = 1 To n - 1
        If r(i, 0) < a Then a = r(i, 0)
        If r(i, 0) > b Then b = r(i, 0)
    Next i
    found_w = b - a
End Function

Private Function found_h(ByVal v As clsVung) As Double
    Dim r() As Double, n As Long, i As Long, a As Double, b As Double
    r = v.ring: n = UBound(r, 1)
    a = r(0, 1): b = r(0, 1)
    For i = 1 To n - 1
        If r(i, 1) < a Then a = r(i, 1)
        If r(i, 1) > b Then b = r(i, 1)
    Next i
    found_h = b - a
End Function

Attribute VB_Name = "modTroLy"
'============================================================
' modTroLy - TRO LY LENH tieng Viet (khong can mang / API key)
'   Go cau lenh, vd:
'     tao vung lop 10 ; gan thua lop 13 ; trich luc thua 15
'     tao vung lop 10, 12 roi gan thua lop 13, gan loai dat lop 6
'     trich luc thua 15 ty le 500 ; to mau ; xuat polygon ; chieu dai canh
'   Bo dau tieng Viet, tach thanh tung lenh theo dong tu (tao/gan/trich...),
'   doc so level / so thua, roi goi dung chuc nang co san.
'   Form: frmTroLy (DC_MoTroLy). Thong so mac dinh lay tu ini / form cu.
'============================================================
Option Explicit

Private mLog As String
' Mau ho so dang dung cho tro ly: 0 = Trich luc TT26, 1 = Tach thua, 2 = Hop thua, 3 = Trich luc + Phieu VL
Public gTLMau As Long

Public Sub DC_MoTroLy()
    DC_MoTroLyMau CLng(val(DC_DocCauHinh("AI_MAU", "0")))
End Sub

Public Sub DC_MoTroLyMau(ByVal m As Long)
    If m < 0 Or m > 3 Then m = 0
    gTLMau = m
    DC_GhiCauHinh "AI_MAU", CStr(m)
    DC_MoFormTuTao "frmTroLy"
End Sub

Public Function TL_TenMau(ByVal m As Long) As String
    Select Case m
        Case 1: TL_TenMau = "T" & ChrW(225) & "ch th" & ChrW(7917) & "a " & ChrW(273) & ChrW(7845) & "t (TT26 - m" & ChrW(7851) & "u 22/" & ChrW(272) & "K)"
        Case 2: TL_TenMau = "H" & ChrW(7907) & "p th" & ChrW(7917) & "a " & ChrW(273) & ChrW(7845) & "t (TT26 - m" & ChrW(7851) & "u 22/" & ChrW(272) & "K)"
        Case 3: TL_TenMau = "Tr" & ChrW(237) & "ch l" & ChrW(7909) & "c + Phi" & ChrW(7871) & "u " & ChrW(273) & "o " & ChrW(273) & ChrW(7841) & "c ch" & ChrW(7881) & "nh l" & ChrW(253) & " (m" & ChrW(7851) & "u VL)"
        Case Else: TL_TenMau = "Tr" & ChrW(237) & "ch l" & ChrW(7909) & "c b" & ChrW(7843) & "n " & ChrW(273) & ChrW(7891) & " " & ChrW(273) & ChrW(7883) & "a ch" & ChrW(237) & "nh (TT26)"
    End Select
End Function

Public Function TL_ViDu(ByVal m As Long) As String
    Select Case m
        Case 1: TL_ViDu = "t" & ChrW(7841) & "o v" & ChrW(249) & "ng l" & ChrW(7899) & "p 10; g" & ChrW(225) & "n th" & ChrW(7917) & "a l" & ChrW(7899) & "p 13; t" & ChrW(225) & "ch th" & ChrW(7917) & "a 15 l" & ChrW(7899) & "p c" & ChrW(7855) & "t 18 t" & ChrW(7927) & " l" & ChrW(7879) & " 500"
        Case 2: TL_ViDu = "t" & ChrW(7841) & "o v" & ChrW(249) & "ng l" & ChrW(7899) & "p 10; g" & ChrW(225) & "n th" & ChrW(7917) & "a l" & ChrW(7899) & "p 13; h" & ChrW(7907) & "p th" & ChrW(7917) & "a 12, 13"
        Case Else: TL_ViDu = "t" & ChrW(7841) & "o v" & ChrW(249) & "ng l" & ChrW(7899) & "p 10; g" & ChrW(225) & "n th" & ChrW(7917) & "a l" & ChrW(7899) & "p 13; tr" & ChrW(237) & "ch l" & ChrW(7909) & "c th" & ChrW(7917) & "a 15"
    End Select
End Function

' Chay chuoi lenh -> tra ve nhat ky (moi lenh 1 dong)
Public Function TL_ChayLenh(ByVal cau As String) As String
    Dim s As String, dS As Collection, i As Long
    mLog = ""
    s = Chuan(cau)
    If Len(s) = 0 Then TL_ChayLenh = "(ch" & ChrW(432) & "a nh" & ChrW(7853) & "p l" & ChrW(7879) & "nh)": Exit Function
    Set dS = TachLenh(s)
    If dS.Count = 0 Then
        TL_ChayLenh = "Kh" & ChrW(244) & "ng hi" & ChrW(7875) & "u l" & ChrW(7879) & "nh: " & cau & vbCrLf & GoiY()
        Exit Function
    End If
    For i = 1 To dS.Count
        ChayMot CStr(dS.Item(i))
    Next i
    TL_ChayLenh = mLog
End Function

Private Sub ghi(ByVal s As String)
    If Len(mLog) > 0 Then mLog = mLog & vbCrLf
    mLog = mLog & s
End Sub

Private Function GoiY() As String
    GoiY = "V" & ChrW(237) & " d" & ChrW(7909) & ": t" & ChrW(7841) & "o v" & ChrW(249) & "ng l" & ChrW(7899) & "p 10 ; g" & ChrW(225) & "n th" & ChrW(7917) & "a l" & ChrW(7899) & "p 13 ; tr" & ChrW(237) & "ch l" & ChrW(7909) & "c th" & ChrW(7917) & "a 15 t" & ChrW(7927) & " l" & ChrW(7879) & " 500 ; t" & ChrW(225) & "ch th" & ChrW(7917) & "a 15 l" & ChrW(7899) & "p c" & ChrW(7855) & "t 18 ; h" & ChrW(7907) & "p th" & ChrW(7917) & "a 12, 13 ; " & _
           "g" & ChrW(225) & "n lo" & ChrW(7841) & "i " & ChrW(273) & ChrW(7845) & "t l" & ChrW(7899) & "p 6 ; t" & ChrW(244) & " m" & ChrW(224) & "u ; xu" & ChrW(7845) & "t polygon ; chi" & ChrW(7873) & "u d" & ChrW(224) & "i c" & ChrW(7841) & "nh ; t" & ChrW(236) & "m l" & ChrW(7895) & "i ; t" & ChrW(7855) & "t l" & ChrW(7899) & "p ; b" & ChrW(7853) & "t l" & ChrW(7899) & "p ; l" & ChrW(432) & "u h" & ChrW(7891) & " s" & ChrW(417)
End Function

'------------------------------------------------------------ chuan hoa
Private Function Chuan(ByVal s As String) As String
    s = LCase$(s)
    BoDauNhom s, ChrW(224) & ChrW(225) & ChrW(7843) & ChrW(227) & ChrW(7841) & ChrW(259) & ChrW(7857) & ChrW(7855) & ChrW(7859) & ChrW(7861) & ChrW(7863) & ChrW(226) & ChrW(7847) & ChrW(7845) & ChrW(7849) & ChrW(7851) & ChrW(7853) & ChrW(192) & ChrW(193) & ChrW(7842) & ChrW(195) & ChrW(7840) & ChrW(258) & ChrW(7856) & ChrW(7854) & ChrW(7858) & ChrW(7860) & ChrW(7862) & ChrW(194) & ChrW(7846) & ChrW(7844) & ChrW(7848) & ChrW(7850) & ChrW(7852), "a"
    BoDauNhom s, ChrW(232) & ChrW(233) & ChrW(7867) & ChrW(7869) & ChrW(7865) & ChrW(234) & ChrW(7873) & ChrW(7871) & ChrW(7875) & ChrW(7877) & ChrW(7879) & ChrW(200) & ChrW(201) & ChrW(7866) & ChrW(7868) & ChrW(7864) & ChrW(202) & ChrW(7872) & ChrW(7870) & ChrW(7874) & ChrW(7876) & ChrW(7878), "e"
    BoDauNhom s, ChrW(236) & ChrW(237) & ChrW(7881) & ChrW(297) & ChrW(7883) & ChrW(204) & ChrW(205) & ChrW(7880) & ChrW(296) & ChrW(7882), "i"
    BoDauNhom s, ChrW(242) & ChrW(243) & ChrW(7887) & ChrW(245) & ChrW(7885) & ChrW(244) & ChrW(7891) & ChrW(7889) & ChrW(7893) & ChrW(7895) & ChrW(7897) & ChrW(417) & ChrW(7901) & ChrW(7899) & ChrW(7903) & ChrW(7905) & ChrW(7907) & ChrW(210) & ChrW(211) & ChrW(7886) & ChrW(213) & ChrW(7884) & ChrW(212) & ChrW(7890) & ChrW(7888) & ChrW(7892) & ChrW(7894) & ChrW(7896) & ChrW(416) & ChrW(7900) & ChrW(7898) & ChrW(7902) & ChrW(7904) & ChrW(7906), "o"
    BoDauNhom s, ChrW(249) & ChrW(250) & ChrW(7911) & ChrW(361) & ChrW(7909) & ChrW(432) & ChrW(7915) & ChrW(7913) & ChrW(7917) & ChrW(7919) & ChrW(7921) & ChrW(217) & ChrW(218) & ChrW(7910) & ChrW(360) & ChrW(7908) & ChrW(431) & ChrW(7914) & ChrW(7912) & ChrW(7916) & ChrW(7918) & ChrW(7920), "u"
    BoDauNhom s, ChrW(7923) & ChrW(253) & ChrW(7927) & ChrW(7929) & ChrW(7925) & ChrW(7922) & ChrW(221) & ChrW(7926) & ChrW(7928) & ChrW(7924), "y"
    BoDauNhom s, ChrW(273) & ChrW(272), "d"
    s = Replace(s, vbCr, " ; "): s = Replace(s, vbLf, " ; "): s = Replace(s, vbTab, " ")
    s = Replace(s, " 1:", " "): s = Replace(s, ":", " ")
    s = Replace(s, ".", " ; ")
    Do While InStr(s, "  ") > 0: s = Replace(s, "  ", " "): Loop
    Chuan = " " & Trim$(s) & " "
End Function

Private Sub BoDauNhom(ByRef s As String, ByVal nhom As String, ByVal thay As String)
    Dim i As Long
    For i = 1 To Len(nhom)
        s = Replace(s, Mid$(nhom, i, 1), thay)
    Next i
End Sub

'------------------------------------------------------------ tach lenh theo dong tu
Private Function DongTu() As Variant
    DongTu = Array(" tach thua", " hop thua", " tao vung", " tao topo", " tao thua", " gan ", " trich luc", " to mau", " xuat polygon", _
                   " xuat poly", " tim loi", " chieu dai", " bat lop", " tat lop", " luu ho so", " luu file ho so")
End Function

Private Function TachLenh(ByVal s As String) As Collection
    Dim c As New Collection, vt() As Long, n As Long, i As Long, j As Long, p As Long, dt As Variant, t As Long
    ReDim vt(1 To 200)
    s = Replace(Replace(s, ";", " ; "), ",", " , ")
    s = Replace(s, " roi ", " ; "): s = Replace(s, " sau do ", " ; "): s = Replace(s, " xong ", " ; ")
    For Each dt In DongTu()
        p = 1
        Do
            p = InStr(p, s, dt)
            If p = 0 Then Exit Do
            ' bo trung (vd " xuat poly" nam trong " xuat polygon", " luu ho so" trong " luu file ho so")
            For j = 1 To n
                If Abs(vt(j) - p) < 4 Then Exit For
            Next j
            If j > n And n < 200 Then n = n + 1: vt(n) = p
            p = p + Len(dt)
        Loop
    Next dt
    For i = 2 To n
        t = vt(i): j = i - 1
        Do While j >= 1
            If vt(j) <= t Then Exit Do
            vt(j + 1) = vt(j): j = j - 1
        Loop
        vt(j + 1) = t
    Next i
    For i = 1 To n
        If i < n Then c.Add Mid$(s, vt(i), vt(i + 1) - vt(i)) Else c.Add Mid$(s, vt(i))
    Next i
    Set TachLenh = c
End Function

'------------------------------------------------------------ doc so
' Cac so dung sau tu khoa (vd "lop" -> "10,12")
Private Function SoSau(ByVal s As String, ByVal tuKhoa As String) As String
    Dim p As Long, i As Long, ch As String, kq As String, so As String, dangDoc As Boolean
    p = InStr(s, " " & tuKhoa & " ")
    If p = 0 Then Exit Function
    p = p + Len(tuKhoa) + 2
    For i = p To Len(s)
        ch = Mid$(s, i, 1)
        If ch Like "[0-9]" Then
            so = so & ch: dangDoc = True
        ElseIf ch = " " Or ch = "," Or ch = "+" Or ch = "-" Then
            If Len(so) > 0 Then kq = kq & IIf(Len(kq) > 0, ",", "") & so: so = ""
        ElseIf Mid$(s, i, 2) = "va" Then
            i = i + 1
        Else
            Exit For
        End If
    Next i
    If Len(so) > 0 Then kq = kq & IIf(Len(kq) > 0, ",", "") & so
    SoSau = kq
End Function

Private Function DsLevel(ByVal so As String) As String
    Dim a() As String, i As Long, kq As String
    If Len(so) = 0 Then Exit Function
    a = Split(so, ",")
    For i = 0 To UBound(a)
        kq = kq & IIf(Len(kq) > 0, ",", "") & "Level " & a(i)
    Next i
    DsLevel = kq
End Function

Private Function DauSo(ByVal so As String) As String
    If InStr(so, ",") > 0 Then DauSo = Left$(so, InStr(so, ",") - 1) Else DauSo = so
End Function

'------------------------------------------------------------ thuc thi 1 lenh
Private Sub ChayMot(ByVal c As String)
    Dim lv As String, csdl As String
    csdl = CsdlMacDinh()
    On Error GoTo Loi
    If InStr(c, " tao vung") = 1 Or InStr(c, " tao topo") = 1 Or InStr(c, " tao thua") = 1 Then
        lv = SoSau(c, "lop"): If Len(lv) = 0 Then lv = SoSau(c, "level")
        If Len(lv) = 0 Then lv = DC_DocCauHinh("AI_LV_RANH", "10")
        DC_GhiCauHinh "AI_LV_RANH", lv
        ghi ChrW(9654) & " T" & ChrW(7841) & "o v" & ChrW(249) & "ng (Topology) t" & ChrW(7915) & " l" & ChrW(7899) & "p " & lv & " ..."
        ChayTaoThua DsLevel(lv), "", "", 1, 0, 0.05, "Level 11", 5, 0.3, csdl, "", 0
        ghi "   xong."
    ElseIf InStr(c, " gan ") = 1 Then
        GanTT c, csdl
    ElseIf InStr(c, " tach thua") = 1 Then
        TachHop c, csdl, 1
    ElseIf InStr(c, " hop thua") = 1 Then
        TachHop c, csdl, 2
    ElseIf InStr(c, " trich luc") = 1 Then
        If gTLMau = 1 Or gTLMau = 2 Then TachHop c, csdl, gTLMau Else TrichLuc c, csdl
    ElseIf InStr(c, " to mau") = 1 Then
        ghi ChrW(9654) & " T" & ChrW(244) & " m" & ChrW(224) & "u b" & ChrW(7843) & "n " & ChrW(273) & ChrW(7891) & " hi" & ChrW(7879) & "n tr" & ChrW(7841) & "ng ...": DC_ToMauHienTrang
    ElseIf InStr(c, " xuat poly") = 1 Then
        ghi ChrW(9654) & " Xu" & ChrW(7845) & "t polygon khoanh " & ChrW(273) & ChrW(7845) & "t ...": DC_XuatPolygonKhoanh
    ElseIf InStr(c, " tim loi") = 1 Then
        ghi ChrW(9654) & " M" & ChrW(7903) & " T" & ChrW(236) & "m l" & ChrW(7895) & "i ...": DC_MoTimLoi
    ElseIf InStr(c, " chieu dai") = 1 Then
        ghi ChrW(9654) & " M" & ChrW(7903) & " Chi" & ChrW(7873) & "u d" & ChrW(224) & "i c" & ChrW(7841) & "nh ...": DC_MoChieuDaiCanh
    ElseIf InStr(c, " tat lop") = 1 Then
        ghi ChrW(9654) & " T" & ChrW(7855) & "t l" & ChrW(7899) & "p b" & ChrW(7843) & "n " & ChrW(273) & ChrW(7891) & " (gi" & ChrW(7919) & " l" & ChrW(7899) & "p h" & ChrW(7891) & " s" & ChrW(417) & " / s" & ChrW(417) & " " & ChrW(273) & ChrW(7891) & ") ..."
        DC_TatLopBanDo DC_DocCauHinh("LV_HS", "50"), DC_DocCauHinh("LV_SD", "51")
    ElseIf InStr(c, " bat lop") = 1 Then
        ghi ChrW(9654) & " B" & ChrW(7853) & "t l" & ChrW(7841) & "i l" & ChrW(7899) & "p b" & ChrW(7843) & "n " & ChrW(273) & ChrW(7891) & " ...": DC_BatLopBanDo
    ElseIf InStr(c, " luu") = 1 Then
        ghi ChrW(9654) & " L" & ChrW(432) & "u file h" & ChrW(7891) & " s" & ChrW(417) & " ...": DC_LuuFileHoSo DC_DocCauHinh("LV_HS", "50"), DC_DocCauHinh("LV_SD", "51")
    Else
        ghi "? Kh" & ChrW(244) & "ng hi" & ChrW(7875) & "u: " & Trim$(c)
    End If
    Exit Sub
Loi:
    ghi ChrW(10006) & " L" & ChrW(7895) & "i khi ch" & ChrW(7841) & "y '" & Trim$(c) & "': " & Err.Description
End Sub

' "gan thua lop 13", "gan loai dat lop 6", "gan to lop 8", "gan chu lop 9", "gan dia chi lop 7"
Private Sub GanTT(ByVal c As String, ByVal csdl As String)
    Dim lvSo As String, lvTo As String, lvLoai As String, lvChu As String, lvDC As String, i As Long, phan() As String, p As String
    phan = Split(Replace(c, " gan ", " | "), " , ")
    For i = 0 To UBound(phan)
        p = " " & Trim$(Replace(phan(i), "|", "")) & " "
        If InStr(p, " loai dat ") > 0 Or InStr(p, " loai ") > 0 Then
            lvLoai = DauSo(SoSau(p, "lop"))
        ElseIf InStr(p, " chu ") > 0 Or InStr(p, " ten ") > 0 Then
            lvChu = DauSo(SoSau(p, "lop"))
        ElseIf InStr(p, " dia chi ") > 0 Then
            lvDC = DauSo(SoSau(p, "lop"))
        ElseIf InStr(p, " to ") > 0 Then
            lvTo = DauSo(SoSau(p, "lop"))
        ElseIf InStr(p, " thua ") > 0 Or InStr(p, " so ") > 0 Then
            lvSo = DauSo(SoSau(p, "lop"))
        End If
    Next i
    If Len(lvSo & lvTo & lvLoai & lvChu & lvDC) = 0 Then
        ghi "? G" & ChrW(225) & "n: ch" & ChrW(432) & "a r" & ChrW(245) & " l" & ChrW(7899) & "p (vd: g" & ChrW(225) & "n th" & ChrW(7917) & "a l" & ChrW(7899) & "p 13, g" & ChrW(225) & "n lo" & ChrW(7841) & "i " & ChrW(273) & ChrW(7845) & "t l" & ChrW(7899) & "p 6)": Exit Sub
    End If
    ghi ChrW(9654) & " G" & ChrW(225) & "n th" & ChrW(244) & "ng tin t" & ChrW(7915) & " nh" & ChrW(227) & "n:" & IIf(Len(lvSo) > 0, " s" & ChrW(7889) & " th" & ChrW(7917) & "a=l" & ChrW(7899) & "p " & lvSo, "") & IIf(Len(lvLoai) > 0, " lo" & ChrW(7841) & "i " & ChrW(273) & ChrW(7845) & "t=l" & ChrW(7899) & "p " & lvLoai, "") & _
        IIf(Len(lvTo) > 0, " t" & ChrW(7901) & "=l" & ChrW(7899) & "p " & lvTo, "") & IIf(Len(lvChu) > 0, " ch" & ChrW(7911) & "=l" & ChrW(7899) & "p " & lvChu, "") & IIf(Len(lvDC) > 0, " " & ChrW(273) & ChrW(7883) & "a ch" & ChrW(7881) & "=l" & ChrW(7899) & "p " & lvDC, "")
    ChayGanTT csdl, lvSo, lvTo, lvLoai, lvChu, lvDC, "", 1, False, False
End Sub

' "trich luc thua 15 [ty le 500] [to 12]"
Private Sub TrichLuc(ByVal c As String, ByVal csdl As String)
    Dim so As String, tL As Double, mau As String, toBD As String, lo As Long
    so = DauSo(SoSau(c, "thua"))
    If Len(so) = 0 Then so = DauSo(SoSau(c, "luc"))
    If Len(so) = 0 Then ghi "? Tr" & ChrW(237) & "ch l" & ChrW(7909) & "c: ch" & ChrW(432) & "a c" & ChrW(243) & " s" & ChrW(7889) & " th" & ChrW(7917) & "a (vd: tr" & ChrW(237) & "ch l" & ChrW(7909) & "c th" & ChrW(7917) & "a 15)": Exit Sub
    tL = val(DauSo(SoSau(c, "le")))
    If tL <= 0 Then tL = val(DC_DocCauHinh("TL_TYLE_TAY", ""))
    If tL <= 0 Then tL = val(DC_DocCauHinh("TL_TYLE", "0"))
    toBD = DauSo(SoSau(c, "to"))
    lo = gTLMau
    If lo = 3 Then
        mau = DC_DocCauHinh("MAU_TL3", "C:\DiaChinhVL\MAU\trichluc.dgn")
        DC_GhiCauHinh "INI_TL", DC_DocCauHinh("INI_TL3", "C:\DiaChinhVL\MAU\trichluc.ini")
    Else
        mau = DC_DocCauHinh("MAU_TL", "C:\DiaChinhVL\TrichLucBanDo_mau.txt")
        DC_GhiCauHinh "INI_TL", DC_DocCauHinh("INI_TL0", DC_DocCauHinh("INI_TL", ""))
    End If
    ghi ChrW(9654) & " [" & TL_TenMau(lo) & "] Tr" & ChrW(237) & "ch l" & ChrW(7909) & "c th" & ChrW(7917) & "a " & so & IIf(tL > 0, " t" & ChrW(7927) & " l" & ChrW(7879) & " 1:" & tL, " (t" & ChrW(7927) & " l" & ChrW(7879) & " t" & ChrW(7921) & " " & ChrW(273) & ChrW(7897) & "ng)") & " ..."
    ChayTrichLuc csdl, so, mau, "T", toBD, DC_DocCauHinh("XA", ""), DC_DocCauHinh("HUYEN", ""), _
                 DC_DocCauHinh("TINH", ""), "", 1, True, tL
End Sub

' "tach thua 15 [lop cat 18] [ty le 500]" ; "hop thua 12, 13 [ty le 500]"
Private Sub TachHop(ByVal c As String, ByVal csdl As String, ByVal cheDo As Long)
    Dim dS As String, tL As Double, mau As String, ini As String, lvCat As String, goc As Collection, Loi As String
    dS = SoSau(c, "thua")
    If Len(dS) = 0 Then dS = SoSau(c, "luc")
    If Len(dS) = 0 Then ghi "? " & IIf(cheDo = 2, "H" & ChrW(7907) & "p", "T" & ChrW(225) & "ch") & " th" & ChrW(7917) & "a: ch" & ChrW(432) & "a c" & ChrW(243) & " s" & ChrW(7889) & " th" & ChrW(7917) & "a": Exit Sub
    If cheDo = 1 Then dS = DauSo(dS)
    If cheDo = 2 And InStr(dS, ",") = 0 Then ghi "? H" & ChrW(7907) & "p th" & ChrW(7917) & "a: c" & ChrW(7847) & "n " & ChrW(237) & "t nh" & ChrW(7845) & "t 2 th" & ChrW(7917) & "a (vd: h" & ChrW(7907) & "p th" & ChrW(7917) & "a 12, 13)": Exit Sub
    tL = val(DauSo(SoSau(c, "le")))
    If tL <= 0 Then tL = val(DC_DocCauHinh("TL_TYLE_TAY", ""))
    If tL <= 0 Then tL = val(DC_DocCauHinh("TL_TYLE", "0"))
    If cheDo = 1 Then
        mau = DC_DocCauHinh("MAU_TACH", "C:\DiaChinhVL\MAU\22tach.dgn")
        ini = DC_DocCauHinh("INI_TACH", "C:\DiaChinhVL\MAU\22tach.ini")
        lvCat = DauSo(SoSau(c, "cat"))
        If Len(lvCat) = 0 Then lvCat = DC_DocCauHinh("TACH_LV", "18")
    Else
        mau = DC_DocCauHinh("MAU_HOP", "C:\DiaChinhVL\MAU\22hop.dgn")
        ini = DC_DocCauHinh("INI_HOP", "C:\DiaChinhVL\MAU\22hop.ini")
    End If
    Set goc = DC_LayThuaCSDL(csdl, dS, Loi)
    If goc Is Nothing Then ghi ChrW(10006) & " " & Loi: Exit Sub
    ghi ChrW(9654) & " [" & TL_TenMau(cheDo) & "] " & IIf(cheDo = 2, "H" & ChrW(7907) & "p th" & ChrW(7917) & "a ", "T" & ChrW(225) & "ch th" & ChrW(7917) & "a ") & dS & _
        IIf(cheDo = 1, " (l" & ChrW(7899) & "p c" & ChrW(7855) & "t " & lvCat & ")", "") & IIf(tL > 0, " t" & ChrW(7927) & " l" & ChrW(7879) & " 1:" & tL, " (t" & ChrW(7927) & " l" & ChrW(7879) & " t" & ChrW(7921) & " " & ChrW(273) & ChrW(7897) & "ng)") & " ..."
    DC_ChayTachHop cheDo, goc, mau, ini, DauSo(SoSau(c, "to")), DC_DocCauHinh("XA", ""), DC_DocCauHinh("HUYEN", ""), _
                   DC_DocCauHinh("TINH", ""), tL, lvCat
End Sub

Attribute VB_Name = "modVeNhan"
'============================================================
' modVeNhan - VE NHAN THUA tu CSDL (kieu "Ve nhan thua" gCadas/LandMap)
'   Nhan TT26: loai dat ben trai, so thua (tren) / dien tich (duoi), gach ngang.
'   Moi nhan = 1 khoi (cell "NHANTHUA"); tung phan co level + mau rieng.
'   Form: frmVeNhan (menu Ban do -> Ve nhan thua...).
'============================================================
Option Explicit

Public Sub DC_MoVeNhan()
    DC_MoFormTuTao "frmVeNhan"
End Sub

' Tra ve so nhan da ve ; loi <> "" neu khong ve duoc
Public Function VN_VeNhan(ByVal csdl As String, ByVal tyLe As Double, ByVal coMm As Double, _
                          ByVal rongMm As Double, ByVal SoLe As Long, ByVal dauPhay As Boolean, _
                          ByVal nghieng As Boolean, ByVal doiHa As Boolean, _
                          ByVal lvSo As String, ByVal mauSo As Long, ByVal lvDT As String, ByVal mauDt As Long, _
                          ByVal lvLoai As String, ByVal mauLoai As Long, _
                          ByVal tuSo As String, ByVal denSo As String, ByRef Loi As String) As Long
    Dim vungs As Collection, v As clsVung, i As Long, n As Long
    Dim cao As Double, rong As Double
    Loi = ""
    On Error Resume Next
    Set vungs = MoCSDL(csdl)
    On Error GoTo 0
    If vungs Is Nothing Then Loi = "Kh" & ChrW(244) & "ng " & ChrW(273) & ChrW(7885) & "c " & ChrW(273) & ChrW(432) & ChrW(7907) & "c CSDL: " & csdl: Exit Function
    If vungs.Count = 0 Then Loi = "CSDL ch" & ChrW(432) & "a c" & ChrW(243) & " th" & ChrW(7917) & "a n" & ChrW(224) & "o (ch" & ChrW(7841) & "y T" & ChrW(7841) & "o Topology / CSDL tr" & ChrW(432) & ChrW(7899) & "c): " & csdl: Exit Function
    If tyLe <= 0 Then tyLe = 2000
    If coMm <= 0 Then coMm = 1.2
    If rongMm <= 0 Then rongMm = coMm
    cao = coMm * tyLe / 1000#: rong = rongMm * tyLe / 1000#

    Dim oLvSo As Level, oLvDt As Level, oLvLoai As Level
    Set oLvSo = DC_TimLevel(lvSo): Set oLvDt = DC_TimLevel(lvDT): Set oLvLoai = DC_TimLevel(lvLoai)

    Dim coTu As Boolean, coDen As Boolean, gTu As Double, gDen As Double, so As Double
    coTu = IsNumeric(Trim$(tuSo)): coDen = IsNumeric(Trim$(denSo))
    If coTu Then gTu = val(tuSo)
    If coDen Then gDen = val(denSo)

    DatKieuChu cao, rong, nghieng
    For i = 1 To vungs.Count
        Set v = vungs.Item(i)
        If coTu Or coDen Then
            so = val(v.soThua)
            If coTu And so < gTu Then GoTo tiep
            If coDen And so > gDen Then GoTo tiep
        End If
        If VeMotNhan(v, cao, rong, ChuDienTich(v.dt, SoLe, dauPhay, doiHa), _
                     oLvSo, mauSo, oLvDt, mauDt, oLvLoai, mauLoai) Then n = n + 1
tiep:
    Next i
    VN_VeNhan = n
End Function

' Xoa cac khoi nhan "NHANTHUA" (do DiaChinhVL ve) ; tra ve so khoi da xoa
Public Function VN_XoaNhan() As Long
    Dim esc As ElementScanCriteria, ee As ElementEnumerator, dS As New Collection, el As Element, i As Long
    Set esc = New ElementScanCriteria
    esc.ExcludeAllTypes
    esc.IncludeType msdElementTypeCellHeader
    Set ee = ActiveModelReference.Scan(esc)
    On Error Resume Next
    Do While ee.MoveNext
        Set el = ee.Current
        If UCase$(el.AsCellElement.Name) = "NHANTHUA" Then dS.Add el
        Err.Clear
    Loop
    For i = 1 To dS.Count
        ActiveModelReference.RemoveElement dS.Item(i)
        If Err.Number = 0 Then VN_XoaNhan = VN_XoaNhan + 1
        Err.Clear
    Next i
End Function

Private Function ChuDienTich(ByVal dt As Double, ByVal SoLe As Long, ByVal dauPhay As Boolean, ByVal doiHa As Boolean) As String
    Dim x As Double, f As String, nL As Long
    x = dt: nL = SoLe
    If doiHa Then x = dt / 10000#: nL = 4
    If nL < 0 Then nL = 0
    If nL > 4 Then nL = 4
    If nL = 0 Then f = "0" Else f = "0." & String$(nL, "0")
    ChuDienTich = Format$(Round(x, nL), f)
    ChuDienTich = Replace(ChuDienTich, ",", ".")
    If dauPhay Then ChuDienTich = Replace(ChuDienTich, ".", ",")
End Function

Private Sub DatKieuChu(ByVal cao As Double, ByVal rong As Double, ByVal nghieng As Boolean)
    Dim ts As Object
    On Error Resume Next
    Set ts = ActiveSettings.TextStyle
    ts.Height = cao
    ts.Width = rong
    ts.Justification = msdTextJustificationCenterCenter
    ts.IsItalic = nghieng
    ts.Italic = nghieng
    Err.Clear
End Sub

Private Function VeMotNhan(ByVal v As clsVung, ByVal cao As Double, ByVal rong As Double, ByVal sDt As String, _
                           ByVal lvSo As Level, ByVal mauSo As Long, ByVal lvDT As Level, ByVal mauDt As Long, _
                           ByVal lvLoai As Level, ByVal mauLoai As Long) As Boolean
    Dim tu As String, loai As String, w As Double, nua As Double, wl As Double
    Dim els() As Element, n As Long, cel As CellElement, e As Element
    tu = Trim$(v.soThua): loai = Trim$(v.loaiDat)
    If Len(tu) = 0 And Len(sDt) = 0 Then Exit Function
    w = Len(tu) * rong * 0.6
    If Len(sDt) * rong * 0.6 > w Then w = Len(sDt) * rong * 0.6
    nua = w / 2# + cao * 0.2
    ReDim els(0 To 3)
    On Error Resume Next
    Set e = CreateLineElement2(Nothing, Point3dFromXYZ(v.cx - nua, v.cy, 0#), Point3dFromXYZ(v.cx + nua, v.cy, 0#))
    If Not e Is Nothing Then GanLvMau e, lvSo, mauSo: Set els(n) = e: n = n + 1
    If Len(tu) > 0 Then
        Set e = Nothing
        Set e = CreateTextElement1(Nothing, tu, Point3dFromXYZ(v.cx, v.cy + cao * 0.9, 0#), Matrix3dIdentity)
        If Not e Is Nothing Then GanLvMau e, lvSo, mauSo: Set els(n) = e: n = n + 1
    End If
    If Len(sDt) > 0 Then
        Set e = Nothing
        Set e = CreateTextElement1(Nothing, sDt, Point3dFromXYZ(v.cx, v.cy - cao * 0.9, 0#), Matrix3dIdentity)
        If Not e Is Nothing Then GanLvMau e, lvDT, mauDt: Set els(n) = e: n = n + 1
    End If
    If Len(loai) > 0 Then
        wl = Len(loai) * rong * 0.6
        Set e = Nothing
        Set e = CreateTextElement1(Nothing, loai, Point3dFromXYZ(v.cx - nua - wl / 2# - cao * 0.3, v.cy, 0#), Matrix3dIdentity)
        If Not e Is Nothing Then GanLvMau e, lvLoai, mauLoai: Set els(n) = e: n = n + 1
    End If
    If n = 0 Then Exit Function
    ReDim Preserve els(0 To n - 1)
    Err.Clear
    Set cel = CreateCellElement1("NHANTHUA", els, Point3dFromXYZ(v.cx, v.cy, 0#), False)
    If Not cel Is Nothing And Err.Number = 0 Then
        ActiveModelReference.AddElement cel
    Else
        Err.Clear
        Dim i As Long
        For i = 0 To n - 1
            ActiveModelReference.AddElement els(i)
        Next i
    End If
    VeMotNhan = (Err.Number = 0)
    Err.Clear
End Function

Private Sub GanLvMau(ByVal e As Element, ByVal lv As Level, ByVal mau As Long)
    On Error Resume Next
    If Not lv Is Nothing Then Set e.Level = lv
    If mau >= 0 Then e.color = mau
    e.LineWeight = 0
    Err.Clear
End Sub

Attribute VB_Name = "modVeTinh"
'============================================================
' modVeTinh - Xem ban do dang mo tren anh ve tinh (khong can xuat KMZ tay)
'   DC_XemVeTinh  : tao C:\DiaChinhVL\XemVeTinh.html (Leaflet + anh ve tinh)
'                   roi mo bang trinh duyet mac dinh.
'   DC_MoGoogleEarth : tao C:\DiaChinhVL\XemVeTinh.kml roi mo bang
'                   Google Earth Pro (neu may co cai).
'   Toa do: VN-2000, mui chieu 3 do, k0 = 0.9999, kinh tuyen truc lay
'   tu thiet lap (Kinh tuyen truc trong "Thiet lap don vi hanh chinh").
'   Doi datum VN-2000 -> WGS-84 bang 7 tham so (TOWGS84 EPSG:4756).
'   Bo qua level 50, 51 (level tool tu ve: khung trich luc, danh dau loi).
'============================================================
Option Explicit

Private Const PI As Double = 3.14159265358979
Private Const A_ As Double = 6378137#
Private Const F_ As Double = 3.35281066474748E-03     ' 1/298.257223563
Private Const K0 As Double = 0.9999
Private Const MAX_DINH As Long = 300000                ' gioi han so dinh

Private mBuf() As String, mN As Long                  ' bo dem chuoi
Private mMinLa As Double, mMaxLa As Double, mMinLo As Double, mMaxLo As Double
Private mSoDuong As Long, mSoDinh As Long, mSoBo As Long
Private mKTT As Double
Private mDatum7 As Boolean

'------------------------------------------------------------
Public Function DC_KinhTuyenTruc() As Double
    Dim s As String
    s = DC_DocCauHinh("KTT", "105.5")
    DC_KinhTuyenTruc = val(s)
    If DC_KinhTuyenTruc < 100 Or DC_KinhTuyenTruc > 112 Then DC_KinhTuyenTruc = 105.5
End Function

'============================================================
' 1) XEM TREN ANH VE TINH (trinh duyet)
'============================================================
Public Sub DC_XemVeTinh()
    Dim duongJS As String, thuaJS As String, html As String, f As String
    mKTT = DC_KinhTuyenTruc(): mDatum7 = (DC_DocCauHinh("DATUM7", "1") <> "0")

    duongJS = GomDuong(False)
    If mSoDuong = 0 Then
        DC_ThongBao "Kh" & ChrW(244) & "ng " & ChrW(273) & ChrW(7885) & "c " & ChrW(273) & ChrW(432) & ChrW(7907) & "c " & ChrW(273) & ChrW(432) & ChrW(7901) & "ng n" & ChrW(224) & "o c" & ChrW(243) & " t" & ChrW(7885) & "a " & ChrW(273) & ChrW(7897) & " VN-2000 trong b" & ChrW(7843) & "n v" & ChrW(7869) & "." & vbCrLf & _
                    "(C" & ChrW(7847) & "n t" & ChrW(7885) & "a " & ChrW(273) & ChrW(7897) & " th" & ChrW(7853) & "t, " & ChrW(273) & ChrW(417) & "n v" & ChrW(7883) & " m" & ChrW(233) & "t.)", "Xem " & ChrW(7843) & "nh v" & ChrW(7879) & " tinh", vbExclamation
        Exit Sub
    End If
    thuaJS = GomThua(False)

    html = "<!DOCTYPE html><html><head><meta charset=""utf-8"">"
    html = html & "<meta name=""viewport"" content=""width=device-width,initial-scale=1"">"
    html = html & "<title>DiaChinhVL - " & JsEsc(ActiveDesignFile.Name) & "</title>"
    html = html & "<link rel=""stylesheet"" href=""https://unpkg.com/leaflet@1.9.4/dist/leaflet.css"">"
    html = html & "<script src=""https://unpkg.com/leaflet@1.9.4/dist/leaflet.js""></script>"
    html = html & "<style>html,body,#map{height:100%;margin:0}#info{position:absolute;z-index:999;left:50px;top:10px;"
    html = html & "background:#fff;padding:6px 10px;font:13px Arial;border-radius:4px;box-shadow:0 1px 4px #0006}"
    html = html & "#info a{margin-left:8px}</style></head><body><div id=""map""></div>"
    html = html & "<div id=""info""><b>" & JsEsc(ActiveDesignFile.Name) & "</b> &middot; " & mSoDuong & " " & ChrW(273) & ChrW(432) & ChrW(7901) & "ng, " & mSoBo & " th" & ChrW(7917) & "a"
    html = html & " &middot; KTT " & Format$(mKTT, "0.00##") & "&deg;<a id=""gg"" href=""#"" target=""_blank"">M" & ChrW(7903) & " Google Maps t" & ChrW(7841) & "i " & ChrW(273) & ChrW(226) & "y</a></div>"
    html = html & "<script>" & vbLf
    html = html & "var D=" & duongJS & ";" & vbLf
    html = html & "var P=" & thuaJS & ";" & vbLf
    html = html & "var anh=L.tileLayer('https://server.arcgisonline.com/ArcGIS/rest/services/World_Imagery/MapServer/tile/{z}/{y}/{x}',{maxZoom:21,maxNativeZoom:19,attribution:'" & ChrW(7842) & "nh: Esri, Maxar, Earthstar Geographics'});" & vbLf
    html = html & "var osm=L.tileLayer('https://tile.openstreetmap.org/{z}/{x}/{y}.png',{maxZoom:21,maxNativeZoom:19,attribution:'&copy; OpenStreetMap'});" & vbLf
    html = html & "var map=L.map('map',{layers:[anh]});" & vbLf
    html = html & "var gD=L.layerGroup(D.map(function(l){return L.polyline(l,{color:'#ffff00',weight:1.5})})).addTo(map);" & vbLf
    html = html & "var gP=L.layerGroup(P.map(function(t){return L.polygon(t.r,{color:'#00e5ff',weight:1,fillOpacity:0.05})"
    html = html & ".bindPopup('<b>Th" & ChrW(7917) & "a '+t.s+'</b> &middot; T" & ChrW(7901) & " '+t.t+'<br>Lo" & ChrW(7841) & "i " & ChrW(273) & ChrW(7845) & "t: '+t.l+'<br>Di" & ChrW(7879) & "n t" & ChrW(237) & "ch: '+t.d+' m&sup2;'+(t.c?'<br>Ch" & ChrW(7911) & ": '+t.c:''))})).addTo(map);" & vbLf
    html = html & "L.control.layers({'" & ChrW(7842) & "nh v" & ChrW(7879) & " tinh':anh,'B" & ChrW(7843) & "n " & ChrW(273) & ChrW(7891) & " " & ChrW(273) & ChrW(432) & ChrW(7901) & "ng':osm},{'" & ChrW(272) & ChrW(432) & ChrW(7901) & "ng ranh':gD,'Th" & ChrW(7917) & "a (CSDL)':gP}).addTo(map);" & vbLf
    html = html & "L.control.scale({imperial:false}).addTo(map);" & vbLf
    html = html & "map.fitBounds([[" & num(mMinLa) & "," & num(mMinLo) & "],[" & num(mMaxLa) & "," & num(mMaxLo) & "]]);" & vbLf
    html = html & "function cn(){var c=map.getCenter();document.getElementById('gg').href='https://www.google.com/maps/@'+c.lat.toFixed(6)+','+c.lng.toFixed(6)+','+map.getZoom()+'z/data=!3m1!1e3';}" & vbLf
    html = html & "map.on('moveend',cn);cn();" & vbLf
    html = html & "</script></body></html>"

    f = DC_THUMUC & "\XemVeTinh.html"
    If Not GhiFileUtf8(f, html) Then Exit Sub
    Shell "cmd /c start """" """ & f & """", vbHide
End Sub

'============================================================
' 2) MO BANG GOOGLE EARTH PRO (KML)
'============================================================
Public Sub DC_MoGoogleEarth()
    Dim duongK As String, thuaK As String, kml As String, f As String
    mKTT = DC_KinhTuyenTruc(): mDatum7 = (DC_DocCauHinh("DATUM7", "1") <> "0")
    duongK = GomDuong(True)
    If mSoDuong = 0 Then
        DC_ThongBao "Kh" & ChrW(244) & "ng " & ChrW(273) & ChrW(7885) & "c " & ChrW(273) & ChrW(432) & ChrW(7907) & "c " & ChrW(273) & ChrW(432) & ChrW(7901) & "ng n" & ChrW(224) & "o c" & ChrW(243) & " t" & ChrW(7885) & "a " & ChrW(273) & ChrW(7897) & " VN-2000 trong b" & ChrW(7843) & "n v" & ChrW(7869) & ".", "Google Earth", vbExclamation
        Exit Sub
    End If
    thuaK = GomThua(True)

    kml = "<?xml version=""1.0"" encoding=""UTF-8""?>" & vbLf & _
      "<kml xmlns=""http://www.opengis.net/kml/2.2""><Document><name>" & XmlEsc(ActiveDesignFile.Name) & "</name>" & vbLf & _
      "<Style id=""duong""><LineStyle><color>ff00ffff</color><width>1.5</width></LineStyle></Style>" & vbLf & _
      "<Style id=""thua""><LineStyle><color>ffffe500</color><width>1</width></LineStyle><PolyStyle><color>1affe500</color></PolyStyle></Style>" & vbLf & _
      "<Folder><name>Duong ranh</name>" & duongK & "</Folder>" & vbLf & _
      "<Folder><name>Thua (CSDL)</name>" & thuaK & "</Folder>" & vbLf & _
      "</Document></kml>"

    f = DC_THUMUC & "\XemVeTinh.kml"
    If Not GhiFileUtf8(f, kml) Then Exit Sub
    Shell "cmd /c start """" """ & f & """", vbHide
End Sub

'============================================================
' Gom duong tu ban ve -> chuoi JS (mang toa do) hoac KML
'============================================================
Private Function GomDuong(ByVal laKml As Boolean) As String
    Dim esc As ElementScanCriteria, ee As ElementEnumerator
    mN = 0: ReDim mBuf(0 To 1023)
    mSoDuong = 0: mSoDinh = 0
    mMinLa = 90: mMaxLa = -90: mMinLo = 180: mMaxLo = -180

    Set esc = New ElementScanCriteria
    esc.ExcludeAllTypes
    esc.IncludeType msdElementTypeLine
    esc.IncludeType msdElementTypeLineString
    esc.IncludeType msdElementTypeShape
    esc.IncludeType msdElementTypeComplexString
    esc.IncludeType msdElementTypeComplexShape
    Set ee = ActiveModelReference.Scan(esc)
    Do While ee.MoveNext
        If mSoDinh > MAX_DINH Then Exit Do
        If Not LevelBoQua(ee.Current) Then ThemPhanTu ee.Current, laKml
    Loop

    If laKml Then
        GomDuong = Join(CatBuf(), "")
    Else
        GomDuong = "[" & Join(CatBuf(), ",") & "]"
    End If
End Function

Private Function LevelBoQua(ByVal el As Element) As Boolean
    Dim n As Long
    n = DC_LevelSo(el)
    LevelBoQua = (n = 50 Or n = 51)
End Function

Private Sub ThemPhanTu(ByVal el As Element, ByVal laKml As Boolean)
    Dim subs As ElementEnumerator, pts() As Point3d
    On Error Resume Next
    If el.IsComplexElement Then
        Set subs = el.AsComplexElement.GetSubElements
        Do While subs.MoveNext
            ThemPhanTu subs.Current, laKml
        Loop
        Exit Sub
    End If
    If Not el.IsVertexList Then Exit Sub
    Err.Clear
    pts = el.AsVertexList.GetVertices
    If Err.Number <> 0 Then Exit Sub
    On Error GoTo 0

    Dim i As Long, s As String, la As Double, lo As Double
    For i = LBound(pts) To UBound(pts)
        If Not ChuyenToaDo(pts(i).x, pts(i).y, la, lo) Then Exit Sub   ' khong phai VN-2000
        If laKml Then
            s = s & num(lo) & "," & num(la) & ",0 "
        Else
            If Len(s) > 0 Then s = s & ","
            s = s & "[" & num(la) & "," & num(lo) & "]"
        End If
    Next i
    If laKml Then
        s = "<Placemark><styleUrl>#duong</styleUrl><LineString><tessellate>1</tessellate><coordinates>" & s & "</coordinates></LineString></Placemark>"
    Else
        s = "[" & s & "]"
    End If
    ThemBuf s
    mSoDuong = mSoDuong + 1
    mSoDinh = mSoDinh + (UBound(pts) - LBound(pts) + 1)
End Sub

'============================================================
' Gom thua tu CSDL (neu co) -> JS / KML
'============================================================
Private Function GomThua(ByVal laKml As Boolean) As String
    Dim vungs As Collection, v As clsVung, i As Long, j As Long
    Dim r() As Double, s As String, la As Double, lo As Double, ok As Boolean
    mSoBo = 0
    mN = 0: ReDim mBuf(0 To 1023)
    On Error Resume Next
    Set vungs = MoCSDL(CsdlMacDinh())
    On Error GoTo 0
    If vungs Is Nothing Then GoTo Xong

    For i = 1 To vungs.Count
        Set v = vungs.Item(i)
        If v.HasRing Then
            r = v.ring
            s = "": ok = True
            For j = LBound(r, 1) To UBound(r, 1)
                If Not ChuyenToaDo(r(j, 0), r(j, 1), la, lo) Then ok = False: Exit For
                If laKml Then
                    s = s & num(lo) & "," & num(la) & ",0 "
                Else
                    If Len(s) > 0 Then s = s & ","
                    s = s & "[" & num(la) & "," & num(lo) & "]"
                End If
            Next j
            If ok And Len(s) > 0 Then
                If laKml Then
                    s = "<Placemark><name>" & XmlEsc(v.soThua) & "</name><description>" & _
                        XmlEsc("To " & v.SoTo & " - " & v.loaiDat & " - " & Format$(v.dt, "0.0") & " m2 - " & v.TenChu) & _
                        "</description><styleUrl>#thua</styleUrl><Polygon><tessellate>1</tessellate><outerBoundaryIs><LinearRing><coordinates>" & _
                        s & "</coordinates></LinearRing></outerBoundaryIs></Polygon></Placemark>"
                Else
                    s = "{r:[" & s & "],s:'" & JsEsc(v.soThua) & "',t:'" & JsEsc(v.SoTo) & "',l:'" & JsEsc(v.loaiDat) & _
                        "',d:'" & Format$(v.dt, "0.0") & "',c:'" & JsEsc(v.TenChu) & "'}"
                End If
                ThemBuf s
                mSoBo = mSoBo + 1
            End If
        End If
    Next i
Xong:
    If laKml Then
        GomThua = Join(CatBuf(), "")
    Else
        GomThua = "[" & Join(CatBuf(), ",") & "]"
    End If
End Function

'============================================================
' VN-2000 (E = x, N = y; met) -> WGS-84 (do). False neu ngoai pham vi VN
'============================================================
Private Function ChuyenToaDo(ByVal e As Double, ByVal n As Double, _
                             ByRef lat As Double, ByRef lon As Double) As Boolean
    If e < 100000# Or e > 900000# Or n < 900000# Or n > 2700000# Then Exit Function

    Dim e2 As Double, ep2 As Double, e1 As Double, m As Double, mu As Double
    Dim p As Double, c As Double, t As Double, n1 As Double, R1 As Double, d As Double
    Dim sp As Double, la0 As Double, lo0 As Double
    e2 = F_ * (2# - F_): ep2 = e2 / (1# - e2)
    e1 = (1# - Sqr(1# - e2)) / (1# + Sqr(1# - e2))
    m = n / K0
    mu = m / (A_ * (1# - e2 / 4# - 3# * e2 ^ 2 / 64# - 5# * e2 ^ 3 / 256#))
    p = mu + (3# * e1 / 2# - 27# * e1 ^ 3 / 32#) * Sin(2# * mu) _
           + (21# * e1 ^ 2 / 16# - 55# * e1 ^ 4 / 32#) * Sin(4# * mu) _
           + (151# * e1 ^ 3 / 96#) * Sin(6# * mu) _
           + (1097# * e1 ^ 4 / 512#) * Sin(8# * mu)
    sp = Sin(p)
    c = ep2 * Cos(p) ^ 2: t = Tan(p) ^ 2
    n1 = A_ / Sqr(1# - e2 * sp * sp)
    R1 = A_ * (1# - e2) / (1# - e2 * sp * sp) ^ 1.5
    d = (e - 500000#) / (n1 * K0)
    la0 = p - (n1 * Tan(p) / R1) * (d ^ 2 / 2# _
            - (5# + 3# * t + 10# * c - 4# * c ^ 2 - 9# * ep2) * d ^ 4 / 24# _
            + (61# + 90# * t + 298# * c + 45# * t ^ 2 - 252# * ep2 - 3# * c ^ 2) * d ^ 6 / 720#)
    lo0 = mKTT * PI / 180# + (d - (1# + 2# * t + c) * d ^ 3 / 6# _
            + (5# - 2# * c + 28# * t - 3# * c ^ 2 + 8# * ep2 + 24# * t ^ 2) * d ^ 5 / 120#) / Cos(la0)

    ' --- VN-2000 -> WGS-84: 7 tham so (TOWGS84 cua EPSG:4756, QD 05/2007),
    '     quy uoc Position Vector. Tat bang DiaChinhVL.ini -> DATUM7=0
    Dim nn As Double, x As Double, y As Double, Z As Double
    Dim xw As Double, yw As Double, zw As Double
    Dim rx As Double, ry As Double, rz As Double, s As Double, sec As Double, pr As Double, i As Long
    If Not mDatum7 Then
        lat = la0 * 180# / PI: lon = lo0 * 180# / PI
        GoTo CapNhatKhung
    End If
    nn = A_ / Sqr(1# - e2 * Sin(la0) ^ 2)
    x = nn * Cos(la0) * Cos(lo0): y = nn * Cos(la0) * Sin(lo0): Z = nn * (1# - e2) * Sin(la0)
    sec = PI / 180# / 3600#
    rx = -0.00928836 * sec: ry = 0.01975479 * sec: rz = -0.00427372 * sec
    s = 0.252906278 / 1000000#
    xw = -191.90441429 + (1# + s) * (x - rz * y + ry * Z)
    yw = -39.30318279 + (1# + s) * (rz * x + y - rx * Z)
    zw = -111.45032835 + (1# + s) * (-ry * x + rx * y + Z)

    lon = Atn2(yw, xw)
    pr = Sqr(xw * xw + yw * yw)
    lat = Atn(zw / (pr * (1# - e2)))
    For i = 1 To 6
        nn = A_ / Sqr(1# - e2 * Sin(lat) ^ 2)
        lat = Atn((zw + e2 * nn * Sin(lat)) / pr)
    Next i
    lat = lat * 180# / PI: lon = lon * 180# / PI

CapNhatKhung:
    If lat < mMinLa Then mMinLa = lat
    If lat > mMaxLa Then mMaxLa = lat
    If lon < mMinLo Then mMinLo = lon
    If lon > mMaxLo Then mMaxLo = lon
    ChuyenToaDo = True
End Function

Private Function Atn2(ByVal y As Double, ByVal x As Double) As Double
    If x > 0 Then
        Atn2 = Atn(y / x)
    ElseIf x < 0 Then
        Atn2 = Atn(y / x) + IIf(y >= 0, PI, -PI)
    Else
        Atn2 = IIf(y >= 0, PI / 2, -PI / 2)
    End If
End Function

'------------------------------------------------------------ tien ich
Private Function num(ByVal v As Double) As String
    num = Replace(Format$(v, "0.0000000"), ",", ".")      ' luon dau cham
End Function

Private Function JsEsc(ByVal s As String) As String
    s = Replace(s, "\", "\\"): s = Replace(s, "'", "\'")
    s = Replace(s, "<", "&lt;"): s = Replace(s, vbCr, " "): s = Replace(s, vbLf, " ")
    JsEsc = s
End Function

Private Function XmlEsc(ByVal s As String) As String
    s = Replace(s, "&", "&amp;"): s = Replace(s, "<", "&lt;"): s = Replace(s, ">", "&gt;")
    XmlEsc = s
End Function

Private Sub ThemBuf(ByVal s As String)
    If mN > UBound(mBuf) Then ReDim Preserve mBuf(0 To UBound(mBuf) * 2 + 1)
    mBuf(mN) = s
    mN = mN + 1
End Sub

Private Function CatBuf() As String()
    Dim r() As String, i As Long
    If mN = 0 Then
        ReDim r(0 To 0): r(0) = ""
        CatBuf = r
        Exit Function
    End If
    ReDim r(0 To mN - 1)
    For i = 0 To mN - 1: r(i) = mBuf(i): Next i
    CatBuf = r
End Function

Private Function GhiFileUtf8(ByVal path As String, ByVal txt As String) As Boolean
    Dim st As Object
    On Error Resume Next
    If Len(Dir$(DC_THUMUC, vbDirectory)) = 0 Then MkDir DC_THUMUC
    Set st = CreateObject("ADODB.Stream")
    st.Type = 2: st.Charset = "utf-8": st.Open
    st.WriteText txt
    st.SaveToFile path, 2
    st.Close
    If Err.Number <> 0 Then
        DC_ThongBao "Kh" & ChrW(244) & "ng ghi " & ChrW(273) & ChrW(432) & ChrW(7907) & "c file: " & path & vbCrLf & Err.Description, "DiaChinhVL", vbExclamation
        Exit Function
    End If
    GhiFileUtf8 = True
End Function

Attribute VB_Name = "modViTriSo"
'============================================================
' modViTriSo - Vi tri dat SO HIEU DINH ra NGOAI thua (so do tach/hop thua)
'   Xet ca nhom thua (cac thua sau tach / cac thua hop): thu 16 huong quanh
'   dinh, chon huong KHONG nam trong thua nao va gan phan giac goc nhat.
'   Dinh nam giua duong cat (khong ra ngoai duoc) -> theo phan giac.
'   (tach rieng module vi modKhungMau gan cham gioi han 64KB)
'============================================================
Option Explicit

Public Sub DC_HuongSoDinh(ByVal dS As Collection, rg() As Double, ByVal m As Long, ByVal i As Long, _
                          ByVal dao As Boolean, ByVal kcM As Double, dx As Double, dy As Double)
    ' SUA 16/10 (2): them KHOANG HO toi cac canh -> dinh nam tren duong cat
    ' (phia trong) cung dat so vao cho trong, khong de len net.
    Dim bx As Double, by As Double, k As Long, a As Double, cx As Double, cy As Double
    Dim best As Double, sc As Double, X0 As Double, Y0 As Double, px As Double, py As Double
    Dim hoN As Double, ngoai As Boolean
    On Error Resume Next
    PhanGiac rg, m, i, dao, bx, by
    dx = bx: dy = by
    X0 = rg(i, 0): Y0 = rg(i, 1)
    best = -1E+30
    For k = 0 To 23
        a = k * 3.14159265358979 / 12#
        cx = Cos(a): cy = Sin(a)
        px = X0 + cx * kcM: py = Y0 + cy * kcM
        hoN = KhoangHo(dS, px, py) / kcM            ' khoang cach toi canh gan nhat (tinh theo kc)
        If hoN > 0.6 Then hoN = 0.6
        ngoai = Not TrongDS(dS, px, py)
        sc = hoN * 4# + (cx * bx + cy * by) * 0.5
        ' 1 thua: BAT BUOC ra ngoai ; nhieu thua (sau tach / truoc hop): duoc dat
        ' ben trong, chi uu tien nhe phia ngoai, chon cho trong nhat
        If ngoai Then
            If dS.Count <= 1 Then sc = sc + 100# Else sc = sc + 1#
        End If
        If sc > best Then best = sc: dx = cx: dy = cy
    Next k
End Sub

' Khoang cach nho nhat tu (x,y) toi moi canh cua nhom thua
Private Function KhoangHo(ByVal dS As Collection, ByVal x As Double, ByVal y As Double) As Double
    Dim j As Long, kv As Long, v As clsVung, r() As Double, n As Long, i As Long, d As Double, best As Double
    best = 1E+30
    For j = 1 To dS.Count
        Set v = dS.Item(j)
        For kv = 0 To v.dao.Count
            If kv = 0 Then r = v.ring Else r = v.dao.Item(kv)
            n = UBound(r, 1)
            For i = 0 To n - 1
                d = KcDoan(x, y, r(i, 0), r(i, 1), r(i + 1, 0), r(i + 1, 1))
                If d < best Then best = d
            Next i
        Next kv
    Next j
    KhoangHo = best
End Function

Private Function KcDoan(ByVal x As Double, ByVal y As Double, ByVal ax As Double, ByVal ay As Double, _
                        ByVal bx As Double, ByVal by As Double) As Double
    Dim vx As Double, vy As Double, L2 As Double, t As Double
    vx = bx - ax: vy = by - ay: L2 = vx * vx + vy * vy
    If L2 <= 0 Then KcDoan = Sqr((x - ax) ^ 2 + (y - ay) ^ 2): Exit Function
    t = ((x - ax) * vx + (y - ay) * vy) / L2
    If t < 0 Then t = 0
    If t > 1 Then t = 1
    KcDoan = Sqr((x - ax - t * vx) ^ 2 + (y - ay - t * vy) ^ 2)
End Function

' Phan giac goc tai dinh i, huong ra ngoai vong (vong dao: vao trong lo)
Private Sub PhanGiac(r() As Double, ByVal n As Long, ByVal i As Long, ByVal dao As Boolean, dx As Double, dy As Double)
    Dim p As Long, q As Long, ux As Double, uy As Double, wx As Double, wy As Double, L As Double, e As Double
    p = i - 1: If p < 0 Then p = n - 1
    q = i + 1
    ux = r(i, 0) - r(p, 0): uy = r(i, 1) - r(p, 1): L = Sqr(ux * ux + uy * uy): If L > 0 Then ux = ux / L: uy = uy / L
    wx = r(i, 0) - r(q, 0): wy = r(i, 1) - r(q, 1): e = Sqr(wx * wx + wy * wy): If e > 0 Then wx = wx / e: wy = wy / e
    If e > L Then e = L
    dx = ux + wx: dy = uy + wy: L = Sqr(dx * dx + dy * dy)
    If L < 0.2 Then dx = -uy: dy = ux: L = 1
    dx = dx / L: dy = dy / L
    e = e * 0.05
    If DiemTrongPolygon(r, r(i, 0) + dx * e, r(i, 1) + dy * e) Xor dao Then dx = -dx: dy = -dy
End Sub

' Diem (x,y) nam trong thua nao cua nhom ds (trong vong ngoai, ngoai cac lo)
Private Function TrongDS(ByVal dS As Collection, ByVal x As Double, ByVal y As Double) As Boolean
    Dim j As Long, kv As Long, v As clsVung, r() As Double, d() As Double, trongLo As Boolean
    For j = 1 To dS.Count
        Set v = dS.Item(j)
        r = v.ring
        If DiemTrongPolygon(r, x, y) Then
            trongLo = False
            For kv = 1 To v.dao.Count
                d = v.dao.Item(kv)
                If DiemTrongPolygon(d, x, y) Then trongLo = True: Exit For
            Next kv
            If Not trongLo Then TrongDS = True: Exit Function
        End If
    Next j
End Function

Attribute VB_Name = "modXuat"
Option Explicit

'============================================================
' modXuat - Xuat bang thong ke ra Excel + Xoa nhan theo level
' Dung lai: LayCacDoan, GhepVung (modDoc/modHinhHoc),
'           GanTruong (modLoaiDat).
'============================================================

Private Function TenLevelActive() As String
    On Error Resume Next
    TenLevelActive = ActiveSettings.Level.Name
    On Error GoTo 0
End Function


'============================================================
' LENH: XUAT BANG THONG KE RA EXCEL
'============================================================
Public Sub DC_XuatExcel()
    Dim lvRanh As String, lvSo As String, lvLoai As String, lvChu As String
    Dim snapStr As String, snap As Double

    lvRanh = InputBox("TEN level RANH thua:", "Xuat Excel", TenLevelActive())
    lvSo = InputBox("TEN level SO THUA:", "Xuat Excel", "")
    lvLoai = InputBox("TEN level LOAI DAT (de trong = bo qua):", "Xuat Excel", "")
    lvChu = InputBox("TEN level TEN CHU (de trong = bo qua):", "Xuat Excel", "")
    snapStr = InputBox("Dung sai noi diem (snap):", "Xuat Excel", "0.05")
    If snapStr = "" Then Exit Sub
    snap = val(snapStr)
    If snap <= 0 Then snap = 0.05

    ' Doc ranh + ghep vung + gan thuoc tinh
    Dim minX As Double, minY As Double, maxX As Double, maxY As Double
    Dim segs As Collection
    Set segs = LayCacDoan(snap, lvRanh, minX, minY, maxX, maxY)
    If segs.Count = 0 Then
        MsgBox "Khong doc duoc doan ranh nao.", vbExclamation, "Xuat Excel"
        Exit Sub
    End If
    Dim soTia As Long, vungs As Collection
    Set vungs = GhepVung(segs, snap, soTia)
    If vungs.Count = 0 Then
        MsgBox "Khong ghep duoc vung nao.", vbExclamation, "Xuat Excel"
        Exit Sub
    End If
    GanTruong vungs, lvSo, "so_thua"
    If Len(Trim$(lvLoai)) > 0 Then GanTruong vungs, lvLoai, "loai_dat"
    If Len(Trim$(lvChu)) > 0 Then GanTruong vungs, lvChu, "ten_chu"

    ' Sap xep theo so thua (so hoc neu duoc)
    Dim n As Long, idx() As Long, keyv() As Double, i As Long, j As Long
    n = vungs.Count
    ReDim idx(1 To n)
    ReDim keyv(1 To n)
    For i = 1 To n
        idx(i) = i
        keyv(i) = SoThuaSo(vungs.Item(i).soThua)
    Next i
    ' insertion sort theo keyv
    Dim ti As Long
    Dim tk As Double
    For i = 2 To n
        ti = idx(i): tk = keyv(i)
        j = i - 1
        Do While j >= 1
            If keyv(j) > tk Then
                keyv(j + 1) = keyv(j): idx(j + 1) = idx(j): j = j - 1
            Else
                Exit Do
            End If
        Loop
        keyv(j + 1) = tk: idx(j + 1) = ti
    Next i

    ' Mo Excel (lien ket muon, khong can tham chieu)
    Dim xl As Object, wb As Object, ws As Object
    On Error Resume Next
    Set xl = CreateObject("Excel.Application")
    On Error GoTo 0
    If xl Is Nothing Then
        MsgBox "Khong mo duoc Excel. May co cai Excel khong?", vbExclamation, "Xuat Excel"
        Exit Sub
    End If
    xl.Visible = True
    Set wb = xl.Workbooks.Add
    Set ws = wb.Worksheets(1)

    ws.Cells(1, 1).Value = "STT"
    ws.Cells(1, 2).Value = "So thua"
    ws.Cells(1, 3).Value = "Loai dat"
    ws.Cells(1, 4).Value = "Dien tich (m2)"
    ws.Cells(1, 5).Value = "Ten chu"
    ws.Range("A1:E1").Font.Bold = True

    Dim v As clsVung, r As Long
    For i = 1 To n
        Set v = vungs.Item(idx(i))
        r = i + 1
        ws.Cells(r, 1).Value = i
        ws.Cells(r, 2).Value = v.soThua
        ws.Cells(r, 3).Value = v.loaiDat
        ws.Cells(r, 4).Value = Round(v.dt, 1)
        ws.Cells(r, 5).Value = v.TenChu
    Next i

    ' Dong tong
    ws.Cells(n + 2, 3).Value = "Tong:"
    ws.Cells(n + 2, 3).Font.Bold = True
    ws.Cells(n + 2, 4).Formula = "=SUM(D2:D" & (n + 1) & ")"
    ws.Cells(n + 2, 4).Font.Bold = True

    ws.Columns("A:E").AutoFit

    MsgBox "Da xuat " & n & " thua ra Excel." & vbCrLf & _
           "Nho luu file trong Excel neu can giu.", _
           vbInformation, "Xuat Excel"
End Sub

' Doi so thua ra so de sap xep; khong phai so -> day xuong cuoi
Private Function SoThuaSo(ByVal s As String) As Double
    Dim t As String, i As Long, c As String, hasDigit As Boolean
    t = ""
    For i = 1 To Len(s)
        c = Mid$(s, i, 1)
        If c >= "0" And c <= "9" Then t = t & c: hasDigit = True
    Next i
    If hasDigit Then
        SoThuaSo = val(t)
    Else
        SoThuaSo = 1E+18
    End If
End Function


'============================================================
' LENH: XOA NHAN THEO LEVEL
'   Xoa Text + TextNode tren level da chon.
'   Neu nhap "chieu dai toi da", xoa them cac LINE ngan hon nguong do
'   (de xoa gach phan so ma khong dung toi ranh dai).
'============================================================
Public Sub DC_XoaNhanTheoLevel()
    ' SUA 12/10/2026: xoa nhan (chu) + TAM thua (dau + gom 2 net ngan) tren level.
    '   Level go so (11) hoac ten (Level 11), nhieu level cach dau phay.
    '   Mac dinh xoa luon net ngan <= 1 (tam thua do Topology ve).
    Dim lvStr As String, maxStr As String, maxDai As Double
    lvStr = InputBox("Level can xoa nhan / tam thua (vd 11 hoac 11,13):", "Xoa nhan", DC_DocCauHinh("XOANHAN_LV", "11"))
    If Len(Trim$(lvStr)) = 0 Then Exit Sub
    maxStr = InputBox("Xoa ca TAM THUA (net ngan hon, don vi ban ve):" & vbCrLf & _
                      "0 = chi xoa chu", "Xoa nhan", DC_DocCauHinh("XOANHAN_DAI", "1"))
    If Len(Trim$(maxStr)) = 0 Then Exit Sub
    maxDai = val(Replace(maxStr, ",", "."))
    DC_GhiCauHinh "XOANHAN_LV", lvStr
    DC_GhiCauHinh "XOANHAN_DAI", CStr(maxDai)

    Dim dS() As Long, c As Long, i As Long, lvOk As Object
    Set lvOk = CreateObject("Scripting.Dictionary")
    c = DC_DsSoLevel(lvStr, dS)
    For i = 0 To c - 1
        lvOk(CStr(dS(i))) = True
    Next i
    If c = 0 Then MsgBox "Level khong hop le: " & lvStr, vbExclamation, "Xoa nhan": Exit Sub

    Dim esc As New ElementScanCriteria, ee As ElementEnumerator, el As Element
    esc.ExcludeAllTypes
    esc.IncludeType msdElementTypeText
    esc.IncludeType msdElementTypeTextNode
    If maxDai > 0 Then
        esc.IncludeType msdElementTypeLine
        esc.IncludeType msdElementTypeLineString
        esc.IncludeType msdElementTypeEllipse          ' cham tron cua tam thua kieu moi
        esc.IncludeType msdElementTypeCellHeader       ' khoi tam thua "TAMTHUA"
    End If
    Dim arr() As Element, n As Long, pts() As Point3d, dai As Double, k As Long
    ReDim arr(1 To 256)
    Set ee = ActiveModelReference.Scan(esc)
    Do While ee.MoveNext
        Set el = ee.Current
        If lvOk.Exists(CStr(DC_LevelSo(el))) Then
            If el.Type = msdElementTypeLine Or el.Type = msdElementTypeLineString Then
                pts = el.AsVertexList.GetVertices
                dai = 0
                For k = LBound(pts) To UBound(pts) - 1
                    dai = dai + Sqr((pts(k + 1).x - pts(k).x) ^ 2 + (pts(k + 1).y - pts(k).y) ^ 2)
                Next k
                If dai > maxDai Then GoTo tiep
            ElseIf el.Type = msdElementTypeEllipse Then
                If el.Range.High.x - el.Range.Low.x > maxDai Then GoTo tiep
            ElseIf el.Type = msdElementTypeCellHeader Then
                If UCase$(el.AsCellElement.Name) <> "TAMTHUA" Then GoTo tiep
            End If
            n = n + 1
            If n > UBound(arr) Then ReDim Preserve arr(1 To n * 2)
            Set arr(n) = el
        End If
tiep:
    Loop
    If n = 0 Then
        MsgBox "Khong co nhan / tam thua nao tren level: " & lvStr & vbCrLf & _
               "(Tam thua co the nam o level khac - xem level bang Element Information)", vbExclamation, "Xoa nhan"
        Exit Sub
    End If
    On Error Resume Next
    CadInputQueue.SendKeyin "mark"
    For i = 1 To n
        ActiveModelReference.RemoveElement arr(i)
    Next i
    On Error GoTo 0
    RedrawAllViews
    MsgBox "Da xoa " & n & " phan tu (chu + tam thua) tren level: " & lvStr & vbCrLf & _
           "(Sai: key-in undo mark)", vbInformation, "Xoa nhan"
End Sub
